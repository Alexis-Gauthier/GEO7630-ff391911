FME workspace tp2.fmw

Parameters:
- DestDataset_LAS =
- DestDataset_POSTGIS =
- DestDataset_POSTGIS_12 =
- DestDataset_POSTGIS_13 =
- DestDataset_POSTGIS_14 =
- DestDataset_POSTGIS_15 =
- DestDataset_POSTGIS_16 =
- DestDataset_POSTGIS_17 =
- DestDataset_POSTGIS_18 =
- DestDataset_POSTGIS_19 =
- DestDataset_POSTGIS_20 =
- DestDataset_POSTGIS_21 =
- DestDataset_POSTGIS_RASTER =
- SourceDataset_GEOJSON =
- SourceDataset_GEOJSON_3 =
- SourceDataset_GEOTIFF =
- SourceDataset_GEOTIFF_16 =
- SourceDataset_LAS =
- SourceDataset_LAS_5 =
- SourceDataset_LAS_7 =
- SourceDataset_LAS_8 =
- SourceDataset_POSTGIS_RASTER =
- SourceDataset_SHAPEFILE =

Readers:
- GEOTIFF_1: GEOTIFF from $(SourceDataset_GEOTIFF_16) in EPSG:3857
- SHAPEFILE_1: SHAPEFILE from $(SourceDataset_SHAPEFILE)
- GEOJSON_1: GEOJSON from $(SourceDataset_GEOJSON)
- GEOJSON_2: GEOJSON from $(SourceDataset_GEOJSON_3)
- GEOTIFF_2: GEOTIFF from $(SourceDataset_GEOTIFF)
- LAS_1: LAS from $(SourceDataset_LAS_7)
- LAS_2: LAS from $(SourceDataset_LAS_8)
- LAS_3: LAS from $(SourceDataset_LAS)
- LAS_4: LAS from $(SourceDataset_LAS_5) in EPSG:3857
- POSTGIS_RASTER_1: POSTGIS_RASTER from $(SourceDataset_POSTGIS_RASTER) in EPSG:3857

Writers:
- POSTGIS_1: POSTGIS to $(DestDataset_POSTGIS) in EPSG:3857
- POSTGIS_2: POSTGIS to $(DestDataset_POSTGIS_17) in EPSG:3857
- POSTGIS_3: POSTGIS to $(DestDataset_POSTGIS_13) in EPSG:3857
- POSTGIS_4: POSTGIS to $(DestDataset_POSTGIS_21) in EPSG:3857
- POSTGIS_5: POSTGIS to $(DestDataset_POSTGIS_15) in EPSG:3857
- POSTGIS_6: POSTGIS to $(DestDataset_POSTGIS_19) in EPSG:3857
- POSTGIS_7: POSTGIS to $(DestDataset_POSTGIS_12) in EPSG:3857
- POSTGIS_8: POSTGIS to $(DestDataset_POSTGIS_14) in EPSG:3857
- POSTGIS_9: POSTGIS to $(DestDataset_POSTGIS_16) in EPSG:3857
- POSTGIS_RASTER_2: POSTGIS_RASTER to $(DestDataset_POSTGIS_RASTER) in EPSG:3857
- LAS_5: LAS to $(DestDataset_LAS) in EPSG:3857
- POSTGIS_10: POSTGIS to $(DestDataset_POSTGIS_18) in EPSG:3857
- POSTGIS_11: POSTGIS to $(DestDataset_POSTGIS_20) in EPSG:3857

Bookmark: Images aériennes 2002
Note: Importation depuis un lien url des données GEOTIFF d'images aériennes de 2002 / --> Disponible sur le site des données ouvertes de Montréal
GEOTIFF (reader GEOTIFF_2)
    -> NullAttributeMapper_12
Note: Reprojette les données en 3857
Reprojector_8
    DEST = EPSG:32188
    INTERPOLATION_TYPE_NAME = Nearest Neighbor
    RASTER_CELL_SIZE = Preserve Cells
    RASTER_TOLERANCE = 0.0
    REPROJECTED -> RasterPropertyExtractor
    REPROJECTED -> RasterResampler
Note: 1er : RasterPropertyExtractor: / - Détermine le nombre de pixel en X & Y / 2e : RasterResampler : / - Divise le nombre de pixel par 10 / (ex : 16175 x 16175 --> 1618 x 1618)
RasterPropertyExtractor
    <REJECTED> -> RasterPropertyExtractor__Rejected_
RasterPropertyExtractor__Rejected_: Logger
    LOG_FEATURE = LOG_ONLY
    MAXCOORDS = 20
    MAXFEATS = 20
    MESSAGE = Feature is:
    SEVERITY = INFO
RasterResampler
    COLUMNS = 1676
    INTERPOLATION_TYPE_NAME = Nearest Neighbor
    ROWCOL_OR_CELLSIZE = RowsColumns
    ROWS = 1676
    RESAMPLED -> RasterBandPropertyExtractor
    RESAMPLED -> RasterSelector
    <REJECTED> -> RasterResampler__Rejected_
Note: Sélectionne seulement les bandes 0;1;2 (RGB)
RasterSelector
    BAND_LIST = 0:;1:;2:
    SELECTION_MODE = Band and Palette List
    -> Reprojector_3
    <REJECTED> -> RasterSelector__Rejected_
Note: Reprojette les données en 3857
Reprojector_3
    DEST = EPSG:3857
    INTERPOLATION_TYPE_NAME = Nearest Neighbor
    RASTER_CELL_SIZE = Preserve Cells
    RASTER_TOLERANCE = 0.0
    REPROJECTED -> NullAttributeMapper_18
Note: Exportation vers PostGIS Raster
image_aerienne_2002_resample (writer POSTGIS_RASTER_2)
RasterSelector__Rejected_: Logger
    LOG_FEATURE = LOG_ONLY
    MAXCOORDS = 20
    MAXFEATS = 20
    MESSAGE = Feature is:
    SEVERITY = INFO
RasterResampler__Rejected_: Logger
    LOG_FEATURE = LOG_ONLY
    MAXCOORDS = 20
    MAXFEATS = 20
    MESSAGE = Feature is:
    SEVERITY = INFO

Bookmark: Validation des données entrantes
Note: Supprimer / rendre vide les attributs ayant des valeurs NULL
NullAttributeMapper_12
    ATTRCHOICE = All Attributes
    NULL_TREATMENT = Null
    OTHER_VALUE = :
    SOURCE_ATTR_VAL = Null
    -> Reprojector_8

Bookmark: Validation des données sortantes
Note: Supprimer / rendre vide les attributs ayant des valeurs NULL
NullAttributeMapper_18
    ATTRCHOICE = Selected Attributes
    ATTRLIST = annee categorie date mois quart
    NULL_TREATMENT = Null
    OTHER_VALUE = :
    SOURCE_ATTR_VAL = Null
    -> image_aerienne_2002_resample (writer POSTGIS_RASTER_2)

Bookmark: Étape à réaliser avant de pouvoir utiliser le transformer ''RasterSelector''
Note: Permet d'extraire différentes propriétés de l'image matricielle
RasterBandPropertyExtractor
    -> ListExploder
    <REJECTED> -> RasterBandPropertyExtractor__Rejected_
Note: Indique quelle bande (R,G,B) se trouve dans quel index (0,1,2)
ListExploder
    ATTR_ACCUM_MODE = Merge List Attributes
    ATTR_CONFLICT_RES = Use List Attribute Values
    INDEX_ATTR = _element_index
    LIST_ATTR = _band{}
    <REJECTED> -> ListExploder__Rejected_
ListExploder__Rejected_: Logger
    LOG_FEATURE = LOG_ONLY
    MAXCOORDS = 20
    MAXFEATS = 20
    MESSAGE = Feature is:
    SEVERITY = INFO
RasterBandPropertyExtractor__Rejected_: Logger
    LOG_FEATURE = LOG_ONLY
    MAXCOORDS = 20
    MAXFEATS = 20
    MESSAGE = Feature is:
    SEVERITY = INFO

Bookmark: Limites de l'arrondissement Ville-Marie
Note: Importation depuis un lien url des données GeoJSON de limites-administratives-agglomeration (polygones) / --> Disponible sur le site des données ouvertes de Montréal
limites-administratives-agglomeration (reader GEOJSON_1)
    attributes: CODEID int, NOM string, CODEMAMH string, NUM int, ABREV string, TYPE string, COMMENT string, DATEMODIF string
    -> GeometryExtractor_2
Note: Reprojecter en 3857
Reprojector
    DEST = EPSG:3857
    INTERPOLATION_TYPE_NAME = Nearest Neighbor
    RASTER_CELL_SIZE = Preserve Cells
    RASTER_TOLERANCE = 0.0
    REPROJECTED -> AttributeFilter
Note: Tri les arrondissements pour ne conserver que "Ville-Marie"
AttributeFilter
    ATTR_NAME = NOM
    ATTR_VALUES = <Empty>,<Missing>,<Null>,<Unfiltered>,Ville-Marie
    Ville-Marie -> AttributeManager
Note: Nettoie pour ne conserver que les colonnes : / - id / - nom / - _geometry
AttributeManager
    ATTR_TABLE:
      RENAME_SET_VALUE CODEID > codeid
      RENAME_SET_VALUE NOM > nom
      REMOVE CODEMAMH
      REMOVE NUM
      REMOVE ABREV
      REMOVE TYPE
      REMOVE COMMENT
      REMOVE DATEMODIF
    -> GeometryValidator_5
    -> Clipper [CLIPPER]
    -> Clipper_2 [CLIPPER]
Note: Exportation vers PostGIS
limite_ville_marie (writer POSTGIS_11)
    attributes: codeid int8, nom text, _geometry text

Bookmark: Validation des données : Bonne pratique
Note: Crée une valeur "_geometry" à chaque attribut
GeometryExtractor_2
    ATTR = _geometry
    KIND_LONG = FME Binary
    REMOVE_GEOMETRY = No
    -> GeometryValidator_2
    <REJECTED> -> GeometryExtractor__Rejected__2
Note: - Rejette géométries corrompues / dégradées
GeometryValidator_2
    ISSUE_ATTR_NAME = _issues
    PRESETS = Basic Integrity
    REPAIR = Yes
    RULES = NAN_REMOVAL PROCESS_MEASURE]NO]FME_CONTROLLER_QUERY_FILE]transformers/dependencies/geometryvalidator8/NAN_REMOVAL.fme]FME_CONTROLLER_CHOICE]NAN_REMOVAL NULL_REMOVAL FME_CONTROLLER_QUERY_FILE]transformers/dependencies/geometryvalidator8/NULL_REMOVAL.fme]FME_CONTROLLER_CHOICE]NULL_REMOVAL TYPE_REPAIR CONNECT_Z_MODE]FIRST_WINS]ARC_ENDPOINT_TOLERANCE_MODE]Auto]ARC_ENDPOINT_TOLERANCE]<Unused>]FME_CONTROLLER_QUERY_FILE]transformers/dependencies/geometryvalidator8/TYPE_REPAIR.fme]FME_CONTROLLER_CHOICE]TYPE_REPAIR
    SUMMARY = Detailed
    PASSED -> Reprojector
    <REJECTED> -> GeometryValidator__Rejected__2
GeometryValidator__Rejected__2: Logger
    LOG_FEATURE = LOG_ONLY
    MAXCOORDS = 20
    MAXFEATS = 20
    MESSAGE = Feature is:
    SEVERITY = INFO
Note: Bonne pratique : Logger / --> Permet de poursuivre l'exécution malgré les rejets / --> Permet un suivi de tous les rejets, car les logger enregistrent ces informations, ce qui facilite ultiment les 'débugage'
GeometryExtractor__Rejected__2: Logger
    LOG_FEATURE = LOG_ONLY
    MAXCOORDS = 20
    MAXFEATS = 20
    MESSAGE = Feature is:
    SEVERITY = INFO

Bookmark: Validation des données sortantes
Note: - Rejette géométries corrompues / dégradées
GeometryValidator_5
    ISSUE_ATTR_NAME = _issues
    PRESETS = Custom
    REPAIR = Yes
    RULES = NAN_REMOVAL PROCESS_MEASURE]NO]FME_CONTROLLER_QUERY_FILE]transformers/dependencies/geometryvalidator8/NAN_REMOVAL.fme]FME_CONTROLLER_CHOICE]NAN_REMOVAL TYPE_REPAIR CONNECT_Z_MODE]FIRST_WINS]ARC_ENDPOINT_TOLERANCE_MODE]Auto]ARC_ENDPOINT_TOLERANCE]<Unused>]FME_CONTROLLER_QUERY_FILE]transformers/dependencies/geometryvalidator8/TYPE_REPAIR.fme]FME_CONTROLLER_CHOICE]TYPE_REPAIR
    SUMMARY = Detailed
    PASSED -> limite_ville_marie (writer POSTGIS_11)

Bookmark: Crimes
Note: Importation depuis un lien url des données GeoJSON d'Actes Criminels (points) mis à jour quotidiennement / --> Disponible sur le site des données ouvertes de Montréal
Note: Bonne pratique : Logger / --> Permet de poursuivre l'exécution malgré les rejets / --> Permet un suivi de tous les rejets, car les logger enregistrent ces informations, ce qui facilite ultiment les 'débugage'
actes-criminels (reader GEOJSON_2)
    attributes: CATEGORIE string, DATE string, QUART string, PDQ float, X float, Y float, LONGITUDE float, LATITUDE float
    -> GeometryExtractor
Note: Reprojecter en 3857
Reprojector_2
    DEST = EPSG:3857
    INTERPOLATION_TYPE_NAME = Nearest Neighbor
    RASTER_CELL_SIZE = Preserve Cells
    RASTER_TOLERANCE = 0.0
    REPROJECTED -> Clipper [CLIPPEE]
Note: - Conserve seulement les données à l'intérieur de l'arrondissement Ville-Marie
Clipper
    ATTR_ACCUM_MODE = Merge Clipper
    ATTR_CONFLICT_RES = Use Clippee
    BOUNDARY_CASES = Treat as Inside
    CLEANING_TOLERANCE = Automatic
    CLIPPED_ATTR = _clipped
    CLIP_TYPE = Multiple Clippers
    CONNECT_Z_MODE = First Wins
    LINES_AS_SEGMENTS = No
    MEASURE_TYPE = Continuous
    MISSING_VAL_MODE = Compute
    PRESERVE_CLIPPEE_EXTENTS = No
    VAL_SOURCE = Clippee Only
    INSIDE -> DateTimeConverter
    <REJECTED> -> Clipper_4__Rejected_
Note: Convertir la donnée "DATE" de 2023-01-31 pour 20230131 (format FME) / --> Facilite l'intérogation de la donnée
DateTimeConverter
    DATETIME_ATTR = DATE
    OUT_FORMAT = FME
    PASSTHROUGH = NO
    REPAIR_INPUT = YES
    -> Tester_:_2015
    -> Tester_:_2016
    -> Tester_:_2017
    -> Tester_:_2018
    -> Tester_:_2020
    -> Tester_:_2021
    -> Tester_:_2022
    -> Tester_:_2023
    -> Tester_:_2019
    <REJECTED> -> DateTimeConverter__Rejected_
Note: Bonne pratique : Logger / --> Permet de poursuivre l'exécution malgré les rejets / --> Permet un suivi de tous les rejets, car les logger enregistrent ces informations, ce qui facilite ultiment les 'débugage'
DateTimeConverter__Rejected_: Logger
    LOG_FEATURE = LOG_ONLY
    MAXCOORDS = 20
    MAXFEATS = 20
    MESSAGE = Feature is:
    SEVERITY = INFO
Note: Bonne pratique : Logger / --> Permet de poursuivre l'exécution malgré les rejets / --> Permet un suivi de tous les rejets, car les logger enregistrent ces informations, ce qui facilite ultiment les 'débugage'
Clipper_4__Rejected_: Logger
    LOG_FEATURE = LOG_ONLY
    MAXCOORDS = 20
    MAXFEATS = 20
    MESSAGE = Feature is:
    SEVERITY = INFO

Bookmark: Validation des données : Bonne pratique
Note: Crée une valeur "_geometry" à chaque attribut
GeometryExtractor
    ATTR = _geometry
    KIND_LONG = FME Binary
    REMOVE_GEOMETRY = No
    -> GeometryValidator
    <REJECTED> -> GeometryExtractor__Rejected_
Note: - Rejette géométries corrompues / dégradées
GeometryValidator
    ISSUE_ATTR_NAME = _issues
    PRESETS = Basic Integrity
    REPAIR = Yes
    RULES = NAN_REMOVAL PROCESS_MEASURE]NO]FME_CONTROLLER_QUERY_FILE]transformers/dependencies/geometryvalidator8/NAN_REMOVAL.fme]FME_CONTROLLER_CHOICE]NAN_REMOVAL NULL_REMOVAL FME_CONTROLLER_QUERY_FILE]transformers/dependencies/geometryvalidator8/NULL_REMOVAL.fme]FME_CONTROLLER_CHOICE]NULL_REMOVAL TYPE_REPAIR CONNECT_Z_MODE]FIRST_WINS]ARC_ENDPOINT_TOLERANCE_MODE]Auto]ARC_ENDPOINT_TOLERANCE]<Unused>]FME_CONTROLLER_QUERY_FILE]transformers/dependencies/geometryvalidator8/TYPE_REPAIR.fme]FME_CONTROLLER_CHOICE]TYPE_REPAIR
    SUMMARY = Detailed
    PASSED -> AttributeFilter_2
    <REJECTED> -> GeometryValidator__Rejected_
Note: - Choisir uniquement les attributs avec des coordonnées X Y
AttributeFilter_2
    ATTR_NAME = X
    ATTR_VALUES = <Empty>,<Missing>,<Null>,<Unfiltered>
    <UNFILTERED> -> Reprojector_2
GeometryValidator__Rejected_: Logger
    LOG_FEATURE = LOG_ONLY
    MAXCOORDS = 20
    MAXFEATS = 20
    MESSAGE = Feature is:
    SEVERITY = INFO
GeometryExtractor__Rejected_: Logger
    LOG_FEATURE = LOG_ONLY
    MAXCOORDS = 20
    MAXFEATS = 20
    MESSAGE = Feature is:
    SEVERITY = INFO

Bookmark: 2019
Note: Sélectionner seulement les données de 2019
Tester_:_2019
    BOOL_OP = OR
    TEST_CLAUSE = CASE_INSENSITIVE_TEST @Value(DATE) BEGINS_WITH 2019
    TEST_MODE = CASE_INSENSITIVE_TEST
    PASSED -> AttributeCreator_2019
Note: Ajoute colonne "annee" avec la valeur "2019"
AttributeCreator_2019
    ATTR_TABLE = SET_TO annee = 2019
    -> Tester_:_Septembre_2019
    -> Tester_:_Juin_2019
    -> Tester_:_Avril_2019
    -> Tester_:_Decembre_2019
    -> Tester_:_Novembre_2019
    -> Tester_:_Aout_2019
    -> Tester_:_Mai_2019
    -> Tester_:_Mars_2019
    -> Tester_:_Janvier_2019
    -> Tester_:_Octobre_2019
    -> Tester_:_Juillet_2019
    -> Tester_:_Fevrier_2019
Note: Sélectionner seulement les données pour chaque mois
Tester_:_Janvier_2019
    BOOL_OP = COMPOSITE
    COMPOSITE_TEST = 1 AND 2
    TEST_CLAUSE:
      TEST @Value(DATE) >= 20190101
      TEST @Value(DATE) <= 20190131
    TEST_MODE = TEST
    PASSED -> AttributeFilter_Jan2019
Note: Trier les données selon la catégorie d'acte criminel
AttributeFilter_Jan2019
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_janvier2019
Note: - Ajoute la colonne "mois" / - Renomme toutes les colonne en minuscule / - Élimine la colonne "_clipped"
AttributeManager_janvier2019
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = janvier
    USER_EXPOSED_ATTRIBUTES = mois
    -> NullAttributeMapper_5
Tester_:_Fevrier_2019
    BOOL_OP = COMPOSITE
    COMPOSITE_TEST = 1 AND 2
    TEST_CLAUSE:
      TEST @Value(DATE) >= 20190201
      TEST @Value(DATE) <= 20190229
    TEST_MODE = TEST
    PASSED -> AttributeFilter_Fev2019
AttributeFilter_Fev2019
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_fevrier2019
AttributeManager_fevrier2019
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = fevrier
    USER_EXPOSED_ATTRIBUTES = mois
    -> NullAttributeMapper_5
Tester_:_Mars_2019
    BOOL_OP = COMPOSITE
    COMPOSITE_TEST = 1 AND 2
    TEST_CLAUSE:
      TEST @Value(DATE) >= 20190301
      TEST @Value(DATE) <= 20190331
    TEST_MODE = TEST
    PASSED -> AttributeFilter_Mars2019
AttributeFilter_Mars2019
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_mars2019
AttributeManager_mars2019
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = mars
    USER_EXPOSED_ATTRIBUTES = mois
    -> NullAttributeMapper_5
Tester_:_Avril_2019
    BOOL_OP = COMPOSITE
    COMPOSITE_TEST = 1 AND 2
    TEST_CLAUSE:
      TEST @Value(DATE) >= 20190401
      TEST @Value(DATE) <= 20190430
    TEST_MODE = TEST
    PASSED -> AttributeFilter_Avril2019
AttributeFilter_Avril2019
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_avril2019
AttributeManager_avril2019
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = avril
    USER_EXPOSED_ATTRIBUTES = mois
    -> NullAttributeMapper_5
Tester_:_Mai_2019
    BOOL_OP = COMPOSITE
    COMPOSITE_TEST = 1 AND 2
    TEST_CLAUSE:
      TEST @Value(DATE) >= 20190501
      TEST @Value(DATE) <= 20190531
    TEST_MODE = TEST
    PASSED -> AttributeFilter_Mai2019
AttributeFilter_Mai2019
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_mai2019
AttributeManager_mai2019
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = mai
    USER_EXPOSED_ATTRIBUTES = mois
    -> NullAttributeMapper_5
Tester_:_Juin_2019
    BOOL_OP = COMPOSITE
    COMPOSITE_TEST = 1 AND 2
    TEST_CLAUSE:
      TEST @Value(DATE) >= 20190601
      TEST @Value(DATE) <= 20190630
    TEST_MODE = TEST
    PASSED -> AttributeFilter_Juin2019
AttributeFilter_Juin2019
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_juin2019
AttributeManager_juin2019
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = juin
    USER_EXPOSED_ATTRIBUTES = mois
    -> NullAttributeMapper_5
Tester_:_Juillet_2019
    BOOL_OP = COMPOSITE
    COMPOSITE_TEST = 1 AND 2
    TEST_CLAUSE:
      TEST @Value(DATE) >= 20190701
      TEST @Value(DATE) <= 20190731
    TEST_MODE = TEST
    PASSED -> AttributeFilter_Juillet2019
AttributeFilter_Juillet2019
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_juillet2019
AttributeManager_juillet2019
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = juillet
    USER_EXPOSED_ATTRIBUTES = mois
    -> NullAttributeMapper_5
Tester_:_Aout_2019
    BOOL_OP = COMPOSITE
    COMPOSITE_TEST = 1 AND 2
    TEST_CLAUSE:
      TEST @Value(DATE) >= 20190801
      TEST @Value(DATE) <= 20190831
    TEST_MODE = TEST
    PASSED -> AttributeFilter_Aout2019
AttributeFilter_Aout2019
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_aout2019
AttributeManager_aout2019
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = aout
    USER_EXPOSED_ATTRIBUTES = mois
    -> NullAttributeMapper_5
Tester_:_Septembre_2019
    BOOL_OP = COMPOSITE
    COMPOSITE_TEST = 1 AND 2
    TEST_CLAUSE:
      TEST @Value(DATE) >= 20190901
      TEST @Value(DATE) <= 20190930
    TEST_MODE = TEST
    PASSED -> AttributeFilter_Sept2019
AttributeFilter_Sept2019
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_septembre2019
AttributeManager_septembre2019
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = septembre
    USER_EXPOSED_ATTRIBUTES = mois
    -> NullAttributeMapper_5
Tester_:_Octobre_2019
    BOOL_OP = COMPOSITE
    COMPOSITE_TEST = 1 AND 2
    TEST_CLAUSE:
      TEST @Value(DATE) >= 20191001
      TEST @Value(DATE) <= 20191031
    TEST_MODE = TEST
    PASSED -> AttributeFilter_Oct2019
AttributeFilter_Oct2019
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_octobre2019
AttributeManager_octobre2019
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = octobre
    USER_EXPOSED_ATTRIBUTES = mois
Tester_:_Novembre_2019
    BOOL_OP = COMPOSITE
    COMPOSITE_TEST = 1 AND 2
    TEST_CLAUSE:
      TEST @Value(DATE) >= 20191101
      TEST @Value(DATE) <= 20191130
    TEST_MODE = TEST
    PASSED -> AttributeFilter_Nov2019
AttributeFilter_Nov2019
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_novembre2019
AttributeManager_novembre2019
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = novembre
    USER_EXPOSED_ATTRIBUTES = mois
    -> NullAttributeMapper_5
Tester_:_Decembre_2019
    BOOL_OP = COMPOSITE
    COMPOSITE_TEST = 1 AND 2
    TEST_CLAUSE:
      TEST @Value(DATE) >= 20191201
      TEST @Value(DATE) <= 20191231
    TEST_MODE = TEST
    PASSED -> AttributeFilter_Dec2019
AttributeFilter_Dec2019
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_decembre2019
AttributeManager_decembre2019
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = decembre
    USER_EXPOSED_ATTRIBUTES = mois
    -> NullAttributeMapper_5
Note: Exportation vers PostGIS
vol_dans_char_2019 (writer POSTGIS_5)
    attributes: categorie text, date text, quart text, pdq float8, x float8, y float8, longitude float8, latitude float8, _geometry text, mois varchar(200), annee varchar(200)

Bookmark: Validation des données sortantes
Note: Supprimer / rendre vide les attributs ayant des valeurs NULL
NullAttributeMapper_5
    ATTRCHOICE = Selected Attributes
    ATTRLIST = annee categorie date mois quart
    NULL_TREATMENT = Null
    OTHER_VALUE = :
    SOURCE_ATTR_VAL = Null
    -> vol_dans_char_2019 (writer POSTGIS_5)

Bookmark: Crime 2021
Note: Sélectionner seulement les données de 2021
Tester_:_2021
    BOOL_OP = OR
    TEST_CLAUSE = CASE_INSENSITIVE_TEST @Value(DATE) BEGINS_WITH 2021
    TEST_MODE = CASE_INSENSITIVE_TEST
    PASSED -> AttributeCreator_2021
Note: Ajoute colonne "annee" avec la valeur "2021"
AttributeCreator_2021
    ATTR_TABLE = SET_TO annee = 2021
    -> Tester_:_Decembre_2021
    -> Tester_:_Octobre_2021
    -> Tester_:_Juillet_2021
    -> Tester_:_Novembre_2021
    -> Tester_:_Mai_2021
    -> Tester_:_Fevrier_2021
    -> Tester_:_Juin_2021
    -> Tester_:_Avril_2021
    -> Tester_:_Septembre_2021
    -> Tester_:_Aout_2021
    -> Tester_:_Mars_2021
    -> Tester_:_Janvier_2021
Note: Sélectionner seulement les données pour chaque mois
Tester_:_Janvier_2021
    BOOL_OP = COMPOSITE
    COMPOSITE_TEST = 1 AND 2
    TEST_CLAUSE:
      TEST @Value(DATE) >= 20210101
      TEST @Value(DATE) <= 20210131
    TEST_MODE = TEST
    PASSED -> AttributeFilter_Jan2021
Note: Trier les données selon la catégorie d'acte criminel
AttributeFilter_Jan2021
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_janvier2021
Note: - Ajoute la colonne "mois" / - Renomme toutes les colonne en minuscule / - Élimine la colonne "_clipped"
AttributeManager_janvier2021
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = janvier
    USER_EXPOSED_ATTRIBUTES = mois
    -> NullAttributeMapper
Tester_:_Fevrier_2021
    BOOL_OP = COMPOSITE
    COMPOSITE_TEST = 1 AND 2
    TEST_CLAUSE:
      TEST @Value(DATE) >= 20210201
      TEST @Value(DATE) <= 20210229
    TEST_MODE = TEST
    PASSED -> AttributeFilter_Fev2021
AttributeFilter_Fev2021
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_fevrier2021
AttributeManager_fevrier2021
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = fevrier
    USER_EXPOSED_ATTRIBUTES = mois
    -> NullAttributeMapper
Tester_:_Mars_2021
    BOOL_OP = COMPOSITE
    COMPOSITE_TEST = 1 AND 2
    TEST_CLAUSE:
      TEST @Value(DATE) >= 20210301
      TEST @Value(DATE) <= 20210331
    TEST_MODE = TEST
    PASSED -> AttributeFilter_Mars2021
AttributeFilter_Mars2021
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_mars2021
AttributeManager_mars2021
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = mars
    USER_EXPOSED_ATTRIBUTES = mois
    -> NullAttributeMapper
Tester_:_Avril_2021
    BOOL_OP = COMPOSITE
    COMPOSITE_TEST = 1 AND 2
    TEST_CLAUSE:
      TEST @Value(DATE) >= 20210401
      TEST @Value(DATE) <= 20210430
    TEST_MODE = TEST
    PASSED -> AttributeFilter_Avril2021
AttributeFilter_Avril2021
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_avril2021
AttributeManager_avril2021
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = avril
    USER_EXPOSED_ATTRIBUTES = mois
    -> NullAttributeMapper
Tester_:_Mai_2021
    BOOL_OP = COMPOSITE
    COMPOSITE_TEST = 1 AND 2
    TEST_CLAUSE:
      TEST @Value(DATE) >= 20210501
      TEST @Value(DATE) <= 20210531
    TEST_MODE = TEST
    PASSED -> AttributeFilter_Mai2021
AttributeFilter_Mai2021
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_mai2021
AttributeManager_mai2021
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = mai
    USER_EXPOSED_ATTRIBUTES = mois
    -> NullAttributeMapper
Tester_:_Juin_2021
    BOOL_OP = COMPOSITE
    COMPOSITE_TEST = 1 AND 2
    TEST_CLAUSE:
      TEST @Value(DATE) >= 20210601
      TEST @Value(DATE) <= 20210630
    TEST_MODE = TEST
    PASSED -> AttributeFilter_Juin2021
AttributeFilter_Juin2021
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_juin2021
AttributeManager_juin2021
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = juin
    USER_EXPOSED_ATTRIBUTES = mois
    -> NullAttributeMapper
Tester_:_Juillet_2021
    BOOL_OP = COMPOSITE
    COMPOSITE_TEST = 1 AND 2
    TEST_CLAUSE:
      TEST @Value(DATE) >= 20210701
      TEST @Value(DATE) <= 20210731
    TEST_MODE = TEST
    PASSED -> AttributeFilter_Juillet2021
AttributeFilter_Juillet2021
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_juillet2021
AttributeManager_juillet2021
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = juillet
    USER_EXPOSED_ATTRIBUTES = mois
    -> NullAttributeMapper
Tester_:_Aout_2021
    BOOL_OP = COMPOSITE
    COMPOSITE_TEST = 1 AND 2
    TEST_CLAUSE:
      TEST @Value(DATE) >= 20210801
      TEST @Value(DATE) <= 20210831
    TEST_MODE = TEST
    PASSED -> AttributeFilter_Aout2021
AttributeFilter_Aout2021
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_aout2021
AttributeManager_aout2021
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = aout
    USER_EXPOSED_ATTRIBUTES = mois
    -> NullAttributeMapper
Tester_:_Septembre_2021
    BOOL_OP = COMPOSITE
    COMPOSITE_TEST = 1 AND 2
    TEST_CLAUSE:
      TEST @Value(DATE) >= 20210901
      TEST @Value(DATE) <= 20210930
    TEST_MODE = TEST
    PASSED -> AttributeFilter_Sept2021
AttributeFilter_Sept2021
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_septembre2021
AttributeManager_septembre2021
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = septembre
    USER_EXPOSED_ATTRIBUTES = mois
    -> NullAttributeMapper
Tester_:_Octobre_2021
    BOOL_OP = COMPOSITE
    COMPOSITE_TEST = 1 AND 2
    TEST_CLAUSE:
      TEST @Value(DATE) >= 20211001
      TEST @Value(DATE) <= 20211031
    TEST_MODE = TEST
    PASSED -> AttributeFilter_Oct2021
AttributeFilter_Oct2021
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_octobre2021
AttributeManager_octobre2021
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = octobre
    USER_EXPOSED_ATTRIBUTES = mois
    -> NullAttributeMapper
Tester_:_Novembre_2021
    BOOL_OP = COMPOSITE
    COMPOSITE_TEST = 1 AND 2
    TEST_CLAUSE:
      TEST @Value(DATE) >= 20211101
      TEST @Value(DATE) <= 20211130
    TEST_MODE = TEST
    PASSED -> AttributeFilter_Nov2021
AttributeFilter_Nov2021
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_novembre2021
AttributeManager_novembre2021
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = novembre
    USER_EXPOSED_ATTRIBUTES = mois
    -> NullAttributeMapper
Tester_:_Decembre_2021
    BOOL_OP = COMPOSITE
    COMPOSITE_TEST = 1 AND 2
    TEST_CLAUSE:
      TEST @Value(DATE) >= 20211201
      TEST @Value(DATE) <= 20211231
    TEST_MODE = TEST
    PASSED -> AttributeFilter_Dec2021
AttributeFilter_Dec2021
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_decembre2021
AttributeManager_decembre2021
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = decembre
    USER_EXPOSED_ATTRIBUTES = mois
    -> NullAttributeMapper
Note: Exportation vers PostGIS
vol_dans_char_2021 (writer POSTGIS_3)
    attributes: categorie text, date text, quart text, pdq float8, x float8, y float8, longitude float8, latitude float8, _geometry text, mois varchar(200), annee varchar(200)

Bookmark: Validation des données sortantes
Note: Supprimer / rendre vide les attributs ayant des valeurs NULL
NullAttributeMapper
    ATTRCHOICE = Selected Attributes
    ATTRLIST = annee categorie date mois quart
    NULL_TREATMENT = Null
    OTHER_VALUE = :
    SOURCE_ATTR_VAL = Null
    -> vol_dans_char_2021 (writer POSTGIS_3)

Bookmark: 2016
Note: Sélectionner seulement les données de 2016
Tester_:_2016
    BOOL_OP = OR
    TEST_CLAUSE = CASE_INSENSITIVE_TEST @Value(DATE) BEGINS_WITH 2016
    TEST_MODE = CASE_INSENSITIVE_TEST
    PASSED -> AttributeCreator_2016
Note: Ajoute colonne "annee" avec la valeur "2016"
AttributeCreator_2016
    ATTR_TABLE = SET_TO annee = 2016
    -> Tester_:_Avril_2016
    -> Tester_:_Novembre_2016
    -> Tester_:_Mars_2016
    -> Tester_:_Juin_2016
    -> Tester_:_Janvier_2016
    -> Tester_:_Juillet_2016
    -> Tester_:_Septembre_2016
    -> Tester_:_Fevrier_2016
    -> Tester_:_Decembre_2016
    -> Tester_:_Aout_2016
    -> Tester_:_Octobre_2016
    -> Tester_:_Mai_2016
Note: Sélectionner seulement les données pour chaque mois
Tester_:_Janvier_2016
    BOOL_OP = COMPOSITE
    COMPOSITE_TEST = 1 AND 2
    TEST_CLAUSE:
      TEST @Value(DATE) >= 20160101
      TEST @Value(DATE) <= 20160131
    TEST_MODE = TEST
    PASSED -> AttributeFilter_Jan2016
Note: Trier les données selon la catégorie d'acte criminel
AttributeFilter_Jan2016
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_janvier2016
Note: - Ajoute la colonne "mois" / - Renomme toutes les colonne en minuscule / - Élimine la colonne "_clipped"
AttributeManager_janvier2016
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = janvier
    USER_EXPOSED_ATTRIBUTES = mois
    -> NullAttributeMapper_8
Tester_:_Fevrier_2016
    BOOL_OP = COMPOSITE
    COMPOSITE_TEST = 1 AND 2
    TEST_CLAUSE:
      TEST @Value(DATE) >= 20160201
      TEST @Value(DATE) <= 20160229
    TEST_MODE = TEST
    PASSED -> AttributeFilter_Fev2016
AttributeFilter_Fev2016
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_fevrier2016
AttributeManager_fevrier2016
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = fevrier
    USER_EXPOSED_ATTRIBUTES = mois
    -> NullAttributeMapper_8
Tester_:_Mars_2016
    BOOL_OP = COMPOSITE
    COMPOSITE_TEST = 1 AND 2
    TEST_CLAUSE:
      TEST @Value(DATE) >= 20160301
      TEST @Value(DATE) <= 20160331
    TEST_MODE = TEST
    PASSED -> AttributeFilter_Mars2016
AttributeFilter_Mars2016
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_mars2016
AttributeManager_mars2016
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = mars
    USER_EXPOSED_ATTRIBUTES = mois
    -> NullAttributeMapper_8
Tester_:_Avril_2016
    BOOL_OP = COMPOSITE
    COMPOSITE_TEST = 1 AND 2
    TEST_CLAUSE:
      TEST @Value(DATE) >= 20160401
      TEST @Value(DATE) <= 20160430
    TEST_MODE = TEST
    PASSED -> AttributeFilter_Avril2016
AttributeFilter_Avril2016
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_avril2016
AttributeManager_avril2016
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = avril
    USER_EXPOSED_ATTRIBUTES = mois
    -> NullAttributeMapper_8
Tester_:_Mai_2016
    BOOL_OP = COMPOSITE
    COMPOSITE_TEST = 1 AND 2
    TEST_CLAUSE:
      TEST @Value(DATE) >= 20160501
      TEST @Value(DATE) <= 20160531
    TEST_MODE = TEST
    PASSED -> AttributeFilter_Mai2016
AttributeFilter_Mai2016
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_mai2016
AttributeManager_mai2016
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = mai
    USER_EXPOSED_ATTRIBUTES = mois
    -> NullAttributeMapper_8
Tester_:_Juin_2016
    BOOL_OP = COMPOSITE
    COMPOSITE_TEST = 1 AND 2
    TEST_CLAUSE:
      TEST @Value(DATE) >= 20160601
      TEST @Value(DATE) <= 20160630
    TEST_MODE = TEST
    PASSED -> AttributeFilter_Juin2016
AttributeFilter_Juin2016
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_juin2016
AttributeManager_juin2016
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = juin
    USER_EXPOSED_ATTRIBUTES = mois
    -> NullAttributeMapper_8
Tester_:_Juillet_2016
    BOOL_OP = COMPOSITE
    COMPOSITE_TEST = 1 AND 2
    TEST_CLAUSE:
      TEST @Value(DATE) >= 20160701
      TEST @Value(DATE) <= 20160731
    TEST_MODE = TEST
    PASSED -> AttributeFilter_Juillet2016
AttributeFilter_Juillet2016
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_juillet2016
AttributeManager_juillet2016
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = juillet
    USER_EXPOSED_ATTRIBUTES = mois
    -> NullAttributeMapper_8
Tester_:_Aout_2016
    BOOL_OP = COMPOSITE
    COMPOSITE_TEST = 1 AND 2
    TEST_CLAUSE:
      TEST @Value(DATE) >= 20160801
      TEST @Value(DATE) <= 20160831
    TEST_MODE = TEST
    PASSED -> AttributeFilter_Aout2016
AttributeFilter_Aout2016
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_aout2016
AttributeManager_aout2016
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = aout
    USER_EXPOSED_ATTRIBUTES = mois
    -> NullAttributeMapper_8
Tester_:_Septembre_2016
    BOOL_OP = COMPOSITE
    COMPOSITE_TEST = 1 AND 2
    TEST_CLAUSE:
      TEST @Value(DATE) >= 20160901
      TEST @Value(DATE) <= 20160930
    TEST_MODE = TEST
    PASSED -> AttributeFilter_Sept2016
AttributeFilter_Sept2016
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_septembre2016
AttributeManager_septembre2016
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = septembre
    USER_EXPOSED_ATTRIBUTES = mois
    -> NullAttributeMapper_8
Tester_:_Octobre_2016
    BOOL_OP = COMPOSITE
    COMPOSITE_TEST = 1 AND 2
    TEST_CLAUSE:
      TEST @Value(DATE) >= 20161001
      TEST @Value(DATE) <= 20161031
    TEST_MODE = TEST
    PASSED -> AttributeFilter_Oct2016
AttributeFilter_Oct2016
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_octobre2016
AttributeManager_octobre2016
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = octobre
    USER_EXPOSED_ATTRIBUTES = mois
    -> NullAttributeMapper_8
Tester_:_Novembre_2016
    BOOL_OP = COMPOSITE
    COMPOSITE_TEST = 1 AND 2
    TEST_CLAUSE:
      TEST @Value(DATE) >= 20161101
      TEST @Value(DATE) <= 20161130
    TEST_MODE = TEST
    PASSED -> AttributeFilter_Nov2016
AttributeFilter_Nov2016
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_novembre2016
AttributeManager_novembre2016
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = novembre
    USER_EXPOSED_ATTRIBUTES = mois
    -> NullAttributeMapper_8
Tester_:_Decembre_2016
    BOOL_OP = COMPOSITE
    COMPOSITE_TEST = 1 AND 2
    TEST_CLAUSE:
      TEST @Value(DATE) >= 20161201
      TEST @Value(DATE) <= 20161231
    TEST_MODE = TEST
    PASSED -> AttributeFilter_Dec2016
AttributeFilter_Dec2016
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_decembre2016
AttributeManager_decembre2016
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = decembre
    USER_EXPOSED_ATTRIBUTES = mois
    -> NullAttributeMapper_8
Note: Exportation vers PostGIS
vol_dans_char_2016 (writer POSTGIS_8)
    attributes: categorie text, date text, quart text, pdq float8, x float8, y float8, longitude float8, latitude float8, _geometry text, mois varchar(200), annee varchar(200)

Bookmark: Validation des données sortantes
Note: Supprimer / rendre vide les attributs ayant des valeurs NULL
NullAttributeMapper_8
    ATTRCHOICE = Selected Attributes
    ATTRLIST = annee categorie date mois quart
    NULL_TREATMENT = Null
    OTHER_VALUE = :
    SOURCE_ATTR_VAL = Null
    -> vol_dans_char_2016 (writer POSTGIS_8)

Bookmark: 2016
Note: Sélectionner seulement les données de 2015
Tester_:_2015
    BOOL_OP = OR
    TEST_CLAUSE = CASE_INSENSITIVE_TEST @Value(DATE) BEGINS_WITH 2015
    TEST_MODE = CASE_INSENSITIVE_TEST
    PASSED -> AttributeCreator_2015
Note: Ajoute colonne "annee" avec la valeur "2015"
AttributeCreator_2015
    ATTR_TABLE = SET_TO annee = 2015
    -> Tester_:_Octobre_2015
    -> Tester_:_Mars_2015
    -> Tester_:_Fevrier_2015
    -> Tester_:_Aout_2015
    -> Tester_:_Avril_2015
    -> Tester_:_Novembre_2015
    -> Tester_:_Decembre_2015
    -> Tester_:_Janvier_2015
    -> Tester_:_Juillet_2015
    -> Tester_:_Juin_2015
    -> Tester_:_Septembre_2015
    -> Tester_:_Mai_2015
Note: Sélectionner seulement les données pour chaque mois
Tester_:_Janvier_2015
    BOOL_OP = COMPOSITE
    COMPOSITE_TEST = 1 AND 2
    TEST_CLAUSE:
      TEST @Value(DATE) >= 20150101
      TEST @Value(DATE) <= 20150131
    TEST_MODE = TEST
    PASSED -> AttributeFilter_Jan2015
Note: Trier les données selon la catégorie d'acte criminel
AttributeFilter_Jan2015
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_janvier2015
Note: - Ajoute la colonne "mois" / - Renomme toutes les colonne en minuscule / - Élimine la colonne "_clipped"
AttributeManager_janvier2015
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = janvier
    USER_EXPOSED_ATTRIBUTES = mois
    -> NullAttributeMapper_9
Tester_:_Fevrier_2015
    BOOL_OP = COMPOSITE
    COMPOSITE_TEST = 1 AND 2
    TEST_CLAUSE:
      TEST @Value(DATE) >= 20150201
      TEST @Value(DATE) <= 20150229
    TEST_MODE = TEST
    PASSED -> AttributeFilter_Fev2015
AttributeFilter_Fev2015
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_fevrier2015
AttributeManager_fevrier2015
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = fevrier
    USER_EXPOSED_ATTRIBUTES = mois
    -> NullAttributeMapper_9
Tester_:_Mars_2015
    BOOL_OP = COMPOSITE
    COMPOSITE_TEST = 1 AND 2
    TEST_CLAUSE:
      TEST @Value(DATE) >= 20150301
      TEST @Value(DATE) <= 20150331
    TEST_MODE = TEST
    PASSED -> AttributeFilter_Mars2015
AttributeFilter_Mars2015
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_mars2015
AttributeManager_mars2015
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = mars
    USER_EXPOSED_ATTRIBUTES = mois
    -> NullAttributeMapper_9
Tester_:_Avril_2015
    BOOL_OP = COMPOSITE
    COMPOSITE_TEST = 1 AND 2
    TEST_CLAUSE:
      TEST @Value(DATE) >= 20150401
      TEST @Value(DATE) <= 20150430
    TEST_MODE = TEST
    PASSED -> AttributeFilter_Avril2015
AttributeFilter_Avril2015
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_avril2015
AttributeManager_avril2015
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = avril
    USER_EXPOSED_ATTRIBUTES = mois
    -> NullAttributeMapper_9
Tester_:_Mai_2015
    BOOL_OP = COMPOSITE
    COMPOSITE_TEST = 1 AND 2
    TEST_CLAUSE:
      TEST @Value(DATE) >= 20150501
      TEST @Value(DATE) <= 20150531
    TEST_MODE = TEST
    PASSED -> AttributeFilter_Mai2015
AttributeFilter_Mai2015
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_mai2015
AttributeManager_mai2015
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = mai
    USER_EXPOSED_ATTRIBUTES = mois
    -> NullAttributeMapper_9
Tester_:_Juin_2015
    BOOL_OP = COMPOSITE
    COMPOSITE_TEST = 1 AND 2
    TEST_CLAUSE:
      TEST @Value(DATE) >= 20150601
      TEST @Value(DATE) <= 20150630
    TEST_MODE = TEST
    PASSED -> AttributeFilter_Juin2015
AttributeFilter_Juin2015
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_juin2015
AttributeManager_juin2015
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = juin
    USER_EXPOSED_ATTRIBUTES = mois
    -> NullAttributeMapper_9
Tester_:_Juillet_2015
    BOOL_OP = COMPOSITE
    COMPOSITE_TEST = 1 AND 2
    TEST_CLAUSE:
      TEST @Value(DATE) >= 20150701
      TEST @Value(DATE) <= 20150731
    TEST_MODE = TEST
    PASSED -> AttributeFilter_Juillet2015
AttributeFilter_Juillet2015
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_juillet2015
AttributeManager_juillet2015
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = juillet
    USER_EXPOSED_ATTRIBUTES = mois
Tester_:_Aout_2015
    BOOL_OP = COMPOSITE
    COMPOSITE_TEST = 1 AND 2
    TEST_CLAUSE:
      TEST @Value(DATE) >= 20150801
      TEST @Value(DATE) <= 20150831
    TEST_MODE = TEST
    PASSED -> AttributeFilter_Aout2015
AttributeFilter_Aout2015
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_aout2015
AttributeManager_aout2015
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = aout
    USER_EXPOSED_ATTRIBUTES = mois
    -> NullAttributeMapper_9
Tester_:_Septembre_2015
    BOOL_OP = COMPOSITE
    COMPOSITE_TEST = 1 AND 2
    TEST_CLAUSE:
      TEST @Value(DATE) >= 20150901
      TEST @Value(DATE) <= 20150930
    TEST_MODE = TEST
    PASSED -> AttributeFilter_Sept2015
AttributeFilter_Sept2015
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_septembre2015
AttributeManager_septembre2015
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = septembre
    USER_EXPOSED_ATTRIBUTES = mois
    -> NullAttributeMapper_9
Tester_:_Octobre_2015
    BOOL_OP = COMPOSITE
    COMPOSITE_TEST = 1 AND 2
    TEST_CLAUSE:
      TEST @Value(DATE) >= 20151001
      TEST @Value(DATE) <= 20151031
    TEST_MODE = TEST
    PASSED -> AttributeFilter_Oct2015
AttributeFilter_Oct2015
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_octobre2015
AttributeManager_octobre2015
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = octobre
    USER_EXPOSED_ATTRIBUTES = mois
    -> NullAttributeMapper_9
Tester_:_Novembre_2015
    BOOL_OP = COMPOSITE
    COMPOSITE_TEST = 1 AND 2
    TEST_CLAUSE:
      TEST @Value(DATE) >= 20151101
      TEST @Value(DATE) <= 20151130
    TEST_MODE = TEST
    PASSED -> AttributeFilter_Nov2015
AttributeFilter_Nov2015
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_novembre2015
AttributeManager_novembre2015
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = novembre
    USER_EXPOSED_ATTRIBUTES = mois
    -> NullAttributeMapper_9
Tester_:_Decembre_2015
    BOOL_OP = COMPOSITE
    COMPOSITE_TEST = 1 AND 2
    TEST_CLAUSE:
      TEST @Value(DATE) >= 20151201
      TEST @Value(DATE) <= 20151231
    TEST_MODE = TEST
    PASSED -> AttributeFilter_Dec2015
AttributeFilter_Dec2015
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_decembre2015
AttributeManager_decembre2015
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = decembre
    USER_EXPOSED_ATTRIBUTES = mois
    -> NullAttributeMapper_9
Note: Exportation vers PostGIS
vol_dans_char_2015 (writer POSTGIS_9)
    attributes: categorie text, date text, quart text, pdq float8, x float8, y float8, longitude float8, latitude float8, _geometry text, mois varchar(200), annee varchar(200)

Bookmark: Validation des données sortantes
Note: Supprimer / rendre vide les attributs ayant des valeurs NULL
NullAttributeMapper_9
    ATTRCHOICE = Selected Attributes
    ATTRLIST = annee categorie date mois quart
    NULL_TREATMENT = Null
    OTHER_VALUE = :
    SOURCE_ATTR_VAL = Null
    -> vol_dans_char_2015 (writer POSTGIS_9)

Bookmark: 2020
Note: Sélectionner seulement les données de 2020
Tester_:_2020
    BOOL_OP = OR
    TEST_CLAUSE = CASE_INSENSITIVE_TEST @Value(DATE) BEGINS_WITH 2020
    TEST_MODE = CASE_INSENSITIVE_TEST
    PASSED -> AttributeCreator_2020
Note: Ajoute colonne "annee" avec la valeur "2020"
AttributeCreator_2020
    ATTR_TABLE = SET_TO annee = 2020
    -> Tester_:_Decembre_2020
    -> Tester_:_Octobre_2020
    -> Tester_:_Juillet_2020
    -> Tester_:_Fevrier_2020
    -> Tester_:_Mai_2020
    -> Tester_:_Mars_2020
    -> Tester_:_Janvier_2020
    -> Tester_:_Novembre_2020
    -> Tester_:_Juin_2020
    -> Tester_:_Septembre_2020
    -> Tester_:_Aout_2020
    -> Tester_:_Avril_2020
Note: Sélectionner seulement les données pour chaque mois
Tester_:_Janvier_2020
    BOOL_OP = COMPOSITE
    COMPOSITE_TEST = 1 AND 2
    TEST_CLAUSE:
      TEST @Value(DATE) >= 20200101
      TEST @Value(DATE) <= 20200131
    TEST_MODE = TEST
    PASSED -> AttributeFilter_Jan2020
Note: Trier les données selon la catégorie d'acte criminel
AttributeFilter_Jan2020
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_janvier2020
Note: - Ajoute la colonne "mois" / - Renomme toutes les colonne en minuscule / - Élimine la colonne "_clipped"
AttributeManager_janvier2020
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = janvier
    USER_EXPOSED_ATTRIBUTES = mois
    -> NullAttributeMapper_4
Tester_:_Fevrier_2020
    BOOL_OP = COMPOSITE
    COMPOSITE_TEST = 1 AND 2
    TEST_CLAUSE:
      TEST @Value(DATE) >= 20200201
      TEST @Value(DATE) <= 20200229
    TEST_MODE = TEST
    PASSED -> AttributeFilter_Fev2020
AttributeFilter_Fev2020
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_fevrier2020
AttributeManager_fevrier2020
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = fevrier
    USER_EXPOSED_ATTRIBUTES = mois
    -> NullAttributeMapper_4
Tester_:_Mars_2020
    BOOL_OP = COMPOSITE
    COMPOSITE_TEST = 1 AND 2
    TEST_CLAUSE:
      TEST @Value(DATE) >= 20200301
      TEST @Value(DATE) <= 20200331
    TEST_MODE = TEST
    PASSED -> AttributeFilter_Mars2020
AttributeFilter_Mars2020
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_mars2020
AttributeManager_mars2020
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = mars
    USER_EXPOSED_ATTRIBUTES = mois
    -> NullAttributeMapper_4
Tester_:_Avril_2020
    BOOL_OP = COMPOSITE
    COMPOSITE_TEST = 1 AND 2
    TEST_CLAUSE:
      TEST @Value(DATE) >= 20200401
      TEST @Value(DATE) <= 20200430
    TEST_MODE = TEST
    PASSED -> AttributeFilter_Avril2020
AttributeFilter_Avril2020
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_avril2020
AttributeManager_avril2020
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = avril
    USER_EXPOSED_ATTRIBUTES = mois
    -> NullAttributeMapper_4
Tester_:_Mai_2020
    BOOL_OP = COMPOSITE
    COMPOSITE_TEST = 1 AND 2
    TEST_CLAUSE:
      TEST @Value(DATE) >= 20200501
      TEST @Value(DATE) <= 20200531
    TEST_MODE = TEST
    PASSED -> AttributeFilter_Mai2020
AttributeFilter_Mai2020
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_mai2020
AttributeManager_mai2020
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = mai
    USER_EXPOSED_ATTRIBUTES = mois
    -> NullAttributeMapper_4
Tester_:_Juin_2020
    BOOL_OP = COMPOSITE
    COMPOSITE_TEST = 1 AND 2
    TEST_CLAUSE:
      TEST @Value(DATE) >= 20200601
      TEST @Value(DATE) <= 20200630
    TEST_MODE = TEST
    PASSED -> AttributeFilter_Juin2020
AttributeFilter_Juin2020
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_juin2020
AttributeManager_juin2020
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = juin
    USER_EXPOSED_ATTRIBUTES = mois
    -> NullAttributeMapper_4
Tester_:_Juillet_2020
    BOOL_OP = COMPOSITE
    COMPOSITE_TEST = 1 AND 2
    TEST_CLAUSE:
      TEST @Value(DATE) >= 20200701
      TEST @Value(DATE) <= 20200731
    TEST_MODE = TEST
    PASSED -> AttributeFilter_Juillet2020
AttributeFilter_Juillet2020
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_juillet2020
AttributeManager_juillet2020
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = juillet
    USER_EXPOSED_ATTRIBUTES = mois
    -> NullAttributeMapper_4
Tester_:_Aout_2020
    BOOL_OP = COMPOSITE
    COMPOSITE_TEST = 1 AND 2
    TEST_CLAUSE:
      TEST @Value(DATE) >= 20200801
      TEST @Value(DATE) <= 20200831
    TEST_MODE = TEST
    PASSED -> AttributeFilter_Aout2020
AttributeFilter_Aout2020
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_aout2020
AttributeManager_aout2020
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = aout
    USER_EXPOSED_ATTRIBUTES = mois
    -> NullAttributeMapper_4
Tester_:_Septembre_2020
    BOOL_OP = COMPOSITE
    COMPOSITE_TEST = 1 AND 2
    TEST_CLAUSE:
      TEST @Value(DATE) >= 20200901
      TEST @Value(DATE) <= 20200930
    TEST_MODE = TEST
    PASSED -> AttributeFilter_Sept2020
AttributeFilter_Sept2020
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_septembre2020
AttributeManager_septembre2020
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = septembre
    USER_EXPOSED_ATTRIBUTES = mois
    -> NullAttributeMapper_4
Tester_:_Octobre_2020
    BOOL_OP = COMPOSITE
    COMPOSITE_TEST = 1 AND 2
    TEST_CLAUSE:
      TEST @Value(DATE) >= 20201001
      TEST @Value(DATE) <= 20201031
    TEST_MODE = TEST
    PASSED -> AttributeFilter_Oct2020
AttributeFilter_Oct2020
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_octobre2020
AttributeManager_octobre2020
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = octobre
    USER_EXPOSED_ATTRIBUTES = mois
    -> NullAttributeMapper_4
Tester_:_Novembre_2020
    BOOL_OP = COMPOSITE
    COMPOSITE_TEST = 1 AND 2
    TEST_CLAUSE:
      TEST @Value(DATE) >= 20201101
      TEST @Value(DATE) <= 20201130
    TEST_MODE = TEST
    PASSED -> AttributeFilter_Nov2020
AttributeFilter_Nov2020
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_novembre2020
AttributeManager_novembre2020
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = novembre
    USER_EXPOSED_ATTRIBUTES = mois
    -> NullAttributeMapper_4
Tester_:_Decembre_2020
    BOOL_OP = COMPOSITE
    COMPOSITE_TEST = 1 AND 2
    TEST_CLAUSE:
      TEST @Value(DATE) >= 20201201
      TEST @Value(DATE) <= 20201231
    TEST_MODE = TEST
    PASSED -> AttributeFilter_Dec2020
AttributeFilter_Dec2020
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_decembre2020
AttributeManager_decembre2020
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = decembre
    USER_EXPOSED_ATTRIBUTES = mois
    -> NullAttributeMapper_4
Note: Exportation vers PostGIS
vol_dans_char_2020 (writer POSTGIS_4)
    attributes: categorie text, date text, quart text, pdq float8, x float8, y float8, longitude float8, latitude float8, _geometry text, mois varchar(200), annee varchar(200)

Bookmark: Validation des données sortantes
Note: Supprimer / rendre vide les attributs ayant des valeurs NULL
NullAttributeMapper_4
    ATTRCHOICE = Selected Attributes
    ATTRLIST = annee categorie date mois quart
    NULL_TREATMENT = Null
    OTHER_VALUE = :
    SOURCE_ATTR_VAL = Null
    -> vol_dans_char_2020 (writer POSTGIS_4)

Bookmark: 2017
Note: Sélectionner seulement les données de 2017
Tester_:_2017
    BOOL_OP = OR
    TEST_CLAUSE = CASE_INSENSITIVE_TEST @Value(DATE) BEGINS_WITH 2017
    TEST_MODE = CASE_INSENSITIVE_TEST
    PASSED -> AttributeCreator_2017
Note: Ajoute colonne "annee" avec la valeur "2017"
AttributeCreator_2017
    ATTR_TABLE = SET_TO annee = 2017
    -> Tester_:_Novembre_2017
    -> Tester_:_Juin_2017
    -> Tester_:_Avril_2017
    -> Tester_:_Fevrier_2017
    -> Tester_:_Mai_2017
    -> Tester_:_Mars_2017
    -> Tester_:_Janvier_2017
    -> Tester_:_Decembre_2017
    -> Tester_:_Juillet_2017
    -> Tester_:_Octobre_2017
    -> Tester_:_Septembre_2017
    -> Tester_:_Aout_2017
Note: Sélectionner seulement les données pour chaque mois
Tester_:_Janvier_2017
    BOOL_OP = COMPOSITE
    COMPOSITE_TEST = 1 AND 2
    TEST_CLAUSE:
      TEST @Value(DATE) >= 20170101
      TEST @Value(DATE) <= 20170131
    TEST_MODE = TEST
    PASSED -> AttributeFilter_Jan2017
Note: Trier les données selon la catégorie d'acte criminel
AttributeFilter_Jan2017
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_janvier2017
Note: - Ajoute la colonne "mois" / - Renomme toutes les colonne en minuscule / - Élimine la colonne "_clipped"
AttributeManager_janvier2017
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = janvier
    USER_EXPOSED_ATTRIBUTES = mois
    -> NullAttributeMapper_7
Tester_:_Fevrier_2017
    BOOL_OP = COMPOSITE
    COMPOSITE_TEST = 1 AND 2
    TEST_CLAUSE:
      TEST @Value(DATE) >= 20170201
      TEST @Value(DATE) <= 20170229
    TEST_MODE = TEST
    PASSED -> AttributeFilter_Fev2017
AttributeFilter_Fev2017
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_fevrier2017
AttributeManager_fevrier2017
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = fevrier
    USER_EXPOSED_ATTRIBUTES = mois
    -> NullAttributeMapper_7
Tester_:_Mars_2017
    BOOL_OP = COMPOSITE
    COMPOSITE_TEST = 1 AND 2
    TEST_CLAUSE:
      TEST @Value(DATE) >= 20170301
      TEST @Value(DATE) <= 20170331
    TEST_MODE = TEST
    PASSED -> AttributeFilter_Mars2017
AttributeFilter_Mars2017
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_mars2017
AttributeManager_mars2017
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = mars
    USER_EXPOSED_ATTRIBUTES = mois
    -> NullAttributeMapper_7
Tester_:_Avril_2017
    BOOL_OP = COMPOSITE
    COMPOSITE_TEST = 1 AND 2
    TEST_CLAUSE:
      TEST @Value(DATE) >= 20170401
      TEST @Value(DATE) <= 20170430
    TEST_MODE = TEST
    PASSED -> AttributeFilter_Avril2017
AttributeFilter_Avril2017
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_avril2017
AttributeManager_avril2017
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = avril
    USER_EXPOSED_ATTRIBUTES = mois
    -> NullAttributeMapper_7
Tester_:_Mai_2017
    BOOL_OP = COMPOSITE
    COMPOSITE_TEST = 1 AND 2
    TEST_CLAUSE:
      TEST @Value(DATE) >= 20170501
      TEST @Value(DATE) <= 20170531
    TEST_MODE = TEST
    PASSED -> AttributeFilter_Mai2017
AttributeFilter_Mai2017
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_mai2017
AttributeManager_mai2017
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = mai
    USER_EXPOSED_ATTRIBUTES = mois
    -> NullAttributeMapper_7
Tester_:_Juin_2017
    BOOL_OP = COMPOSITE
    COMPOSITE_TEST = 1 AND 2
    TEST_CLAUSE:
      TEST @Value(DATE) >= 20170601
      TEST @Value(DATE) <= 20170630
    TEST_MODE = TEST
    PASSED -> AttributeFilter_Juin2017
AttributeFilter_Juin2017
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_juin2017
AttributeManager_juin2017
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = juin
    USER_EXPOSED_ATTRIBUTES = mois
    -> NullAttributeMapper_7
Tester_:_Juillet_2017
    BOOL_OP = COMPOSITE
    COMPOSITE_TEST = 1 AND 2
    TEST_CLAUSE:
      TEST @Value(DATE) >= 20170701
      TEST @Value(DATE) <= 20170731
    TEST_MODE = TEST
    PASSED -> AttributeFilter_Juillet2017
AttributeFilter_Juillet2017
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_juillet2017
AttributeManager_juillet2017
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = juillet
    USER_EXPOSED_ATTRIBUTES = mois
    -> NullAttributeMapper_7
Tester_:_Aout_2017
    BOOL_OP = COMPOSITE
    COMPOSITE_TEST = 1 AND 2
    TEST_CLAUSE:
      TEST @Value(DATE) >= 20170801
      TEST @Value(DATE) <= 20170831
    TEST_MODE = TEST
    PASSED -> AttributeFilter_Aout2017
AttributeFilter_Aout2017
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_aout2017
AttributeManager_aout2017
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = aout
    USER_EXPOSED_ATTRIBUTES = mois
    -> NullAttributeMapper_7
Tester_:_Septembre_2017
    BOOL_OP = COMPOSITE
    COMPOSITE_TEST = 1 AND 2
    TEST_CLAUSE:
      TEST @Value(DATE) >= 20170901
      TEST @Value(DATE) <= 20170930
    TEST_MODE = TEST
    PASSED -> AttributeFilter_Sept2017
AttributeFilter_Sept2017
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_septembre2017
AttributeManager_septembre2017
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = septembre
    USER_EXPOSED_ATTRIBUTES = mois
    -> NullAttributeMapper_7
Tester_:_Octobre_2017
    BOOL_OP = COMPOSITE
    COMPOSITE_TEST = 1 AND 2
    TEST_CLAUSE:
      TEST @Value(DATE) >= 20171001
      TEST @Value(DATE) <= 20171031
    TEST_MODE = TEST
    PASSED -> AttributeFilter_Oct2017
AttributeFilter_Oct2017
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_octobre2017
AttributeManager_octobre2017
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = octobre
    USER_EXPOSED_ATTRIBUTES = mois
    -> NullAttributeMapper_7
Tester_:_Novembre_2017
    BOOL_OP = COMPOSITE
    COMPOSITE_TEST = 1 AND 2
    TEST_CLAUSE:
      TEST @Value(DATE) >= 20171101
      TEST @Value(DATE) <= 20171130
    TEST_MODE = TEST
    PASSED -> AttributeFilter_Nov2017
AttributeFilter_Nov2017
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_novembre2017
AttributeManager_novembre2017
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = novembre
    USER_EXPOSED_ATTRIBUTES = mois
    -> NullAttributeMapper_7
Tester_:_Decembre_2017
    BOOL_OP = COMPOSITE
    COMPOSITE_TEST = 1 AND 2
    TEST_CLAUSE:
      TEST @Value(DATE) >= 20171201
      TEST @Value(DATE) <= 20171231
    TEST_MODE = TEST
    PASSED -> AttributeFilter_Dec2017
AttributeFilter_Dec2017
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_decembre2017
AttributeManager_decembre2017
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = decembre
    USER_EXPOSED_ATTRIBUTES = mois
    -> NullAttributeMapper_7
Note: Exportation vers PostGIS
vol_dans_char_2017 (writer POSTGIS_7)
    attributes: categorie text, date text, quart text, pdq float8, x float8, y float8, longitude float8, latitude float8, _geometry text, mois varchar(200), annee varchar(200)

Bookmark: Validation des données sortantes
Note: Supprimer / rendre vide les attributs ayant des valeurs NULL
NullAttributeMapper_7
    ATTRCHOICE = Selected Attributes
    ATTRLIST = annee categorie date mois quart
    NULL_TREATMENT = Null
    OTHER_VALUE = :
    SOURCE_ATTR_VAL = Null
    -> vol_dans_char_2017 (writer POSTGIS_7)

Bookmark: 2018
Note: Sélectionner seulement les données de 2018
Tester_:_2018
    BOOL_OP = OR
    TEST_CLAUSE = CASE_INSENSITIVE_TEST @Value(DATE) BEGINS_WITH 2018
    TEST_MODE = CASE_INSENSITIVE_TEST
    PASSED -> AttributeCreator_2018
Note: Ajoute colonne "annee" avec la valeur "2018"
AttributeCreator_2018
    ATTR_TABLE = SET_TO annee = 2018
    -> Tester_:_Octobre_2018
    -> Tester_:_Avril_2018
    -> Tester_:_Juin_2018
    -> Tester_:_Janvier_2018
    -> Tester_:_Fevrier_2018
    -> Tester_:_Septembre_2018
    -> Tester_:_Aout_2018
    -> Tester_:_Decembre_2018
    -> Tester_:_Mars_2018
    -> Tester_:_Novembre_2018
    -> Tester_:_Juillet_2018
    -> Tester_:_Mai_2018
Note: Sélectionner seulement les données pour chaque mois
Tester_:_Janvier_2018
    BOOL_OP = COMPOSITE
    COMPOSITE_TEST = 1 AND 2
    TEST_CLAUSE:
      TEST @Value(DATE) >= 20180101
      TEST @Value(DATE) <= 20180131
    TEST_MODE = TEST
    PASSED -> AttributeFilter_Jan2018
Note: Trier les données selon la catégorie d'acte criminel
AttributeFilter_Jan2018
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_janvier2018
Note: - Ajoute la colonne "mois" / - Renomme toutes les colonne en minuscule / - Élimine la colonne "_clipped"
AttributeManager_janvier2018
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = janvier
    USER_EXPOSED_ATTRIBUTES = mois
    -> NullAttributeMapper_6
Tester_:_Fevrier_2018
    BOOL_OP = COMPOSITE
    COMPOSITE_TEST = 1 AND 2
    TEST_CLAUSE:
      TEST @Value(DATE) >= 20180201
      TEST @Value(DATE) <= 20180229
    TEST_MODE = TEST
    PASSED -> AttributeFilter_Fev2018
AttributeFilter_Fev2018
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_fevrier2018
AttributeManager_fevrier2018
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = fevrier
    USER_EXPOSED_ATTRIBUTES = mois
    -> NullAttributeMapper_6
Tester_:_Mars_2018
    BOOL_OP = COMPOSITE
    COMPOSITE_TEST = 1 AND 2
    TEST_CLAUSE:
      TEST @Value(DATE) >= 20180301
      TEST @Value(DATE) <= 20180331
    TEST_MODE = TEST
    PASSED -> AttributeFilter_Mars2018
AttributeFilter_Mars2018
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_mars2018
AttributeManager_mars2018
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = mars
    USER_EXPOSED_ATTRIBUTES = mois
    -> NullAttributeMapper_6
Tester_:_Avril_2018
    BOOL_OP = COMPOSITE
    COMPOSITE_TEST = 1 AND 2
    TEST_CLAUSE:
      TEST @Value(DATE) >= 20180401
      TEST @Value(DATE) <= 20180430
    TEST_MODE = TEST
    PASSED -> AttributeFilter_Avril2018
AttributeFilter_Avril2018
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_avril2018
AttributeManager_avril2018
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = avril
    USER_EXPOSED_ATTRIBUTES = mois
    -> NullAttributeMapper_6
Tester_:_Mai_2018
    BOOL_OP = COMPOSITE
    COMPOSITE_TEST = 1 AND 2
    TEST_CLAUSE:
      TEST @Value(DATE) >= 20180501
      TEST @Value(DATE) <= 20180531
    TEST_MODE = TEST
    PASSED -> AttributeFilter_Mai2018
AttributeFilter_Mai2018
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_mai2018
AttributeManager_mai2018
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = mai
    USER_EXPOSED_ATTRIBUTES = mois
    -> NullAttributeMapper_6
Tester_:_Juin_2018
    BOOL_OP = COMPOSITE
    COMPOSITE_TEST = 1 AND 2
    TEST_CLAUSE:
      TEST @Value(DATE) >= 20180601
      TEST @Value(DATE) <= 20180630
    TEST_MODE = TEST
    PASSED -> AttributeFilter_Juin2018
AttributeFilter_Juin2018
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_juin2018
AttributeManager_juin2018
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = juin
    USER_EXPOSED_ATTRIBUTES = mois
    -> NullAttributeMapper_6
Tester_:_Juillet_2018
    BOOL_OP = COMPOSITE
    COMPOSITE_TEST = 1 AND 2
    TEST_CLAUSE:
      TEST @Value(DATE) >= 20180701
      TEST @Value(DATE) <= 20180731
    TEST_MODE = TEST
    PASSED -> AttributeFilter_Juillet2018
AttributeFilter_Juillet2018
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_juillet2018
AttributeManager_juillet2018
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = juillet
    USER_EXPOSED_ATTRIBUTES = mois
    -> NullAttributeMapper_6
Tester_:_Aout_2018
    BOOL_OP = COMPOSITE
    COMPOSITE_TEST = 1 AND 2
    TEST_CLAUSE:
      TEST @Value(DATE) >= 20180801
      TEST @Value(DATE) <= 20180831
    TEST_MODE = TEST
    PASSED -> AttributeFilter_Aout2018
AttributeFilter_Aout2018
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_aout2018
AttributeManager_aout2018
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = aout
    USER_EXPOSED_ATTRIBUTES = mois
    -> NullAttributeMapper_6
Tester_:_Septembre_2018
    BOOL_OP = COMPOSITE
    COMPOSITE_TEST = 1 AND 2
    TEST_CLAUSE:
      TEST @Value(DATE) >= 20180901
      TEST @Value(DATE) <= 20180930
    TEST_MODE = TEST
    PASSED -> AttributeFilter_Sept2018
AttributeFilter_Sept2018
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_septembre218
AttributeManager_septembre218
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = septembre
    USER_EXPOSED_ATTRIBUTES = mois
    -> NullAttributeMapper_6
Tester_:_Octobre_2018
    BOOL_OP = COMPOSITE
    COMPOSITE_TEST = 1 AND 2
    TEST_CLAUSE:
      TEST @Value(DATE) >= 20181001
      TEST @Value(DATE) <= 20181031
    TEST_MODE = TEST
    PASSED -> AttributeFilter_Oct2018
AttributeFilter_Oct2018
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_octobre2018
AttributeManager_octobre2018
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = octobre
    USER_EXPOSED_ATTRIBUTES = mois
    -> NullAttributeMapper_6
Tester_:_Novembre_2018
    BOOL_OP = COMPOSITE
    COMPOSITE_TEST = 1 AND 2
    TEST_CLAUSE:
      TEST @Value(DATE) >= 20181101
      TEST @Value(DATE) <= 20181130
    TEST_MODE = TEST
    PASSED -> AttributeFilter_Nov2018
AttributeFilter_Nov2018
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_novembre2018
AttributeManager_novembre2018
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = novembre
    USER_EXPOSED_ATTRIBUTES = mois
    -> NullAttributeMapper_6
Tester_:_Decembre_2018
    BOOL_OP = COMPOSITE
    COMPOSITE_TEST = 1 AND 2
    TEST_CLAUSE:
      TEST @Value(DATE) >= 20181201
      TEST @Value(DATE) <= 20181231
    TEST_MODE = TEST
    PASSED -> AttributeFilter_Dec2018
AttributeFilter_Dec2018
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_decembre2018
AttributeManager_decembre2018
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = decembre
    USER_EXPOSED_ATTRIBUTES = mois
    -> NullAttributeMapper_6
Note: Exportation vers PostGIS
vol_dans_char_2018 (writer POSTGIS_6)
    attributes: categorie text, date text, quart text, pdq float8, x float8, y float8, longitude float8, latitude float8, _geometry text, mois varchar(200), annee varchar(200)

Bookmark: Validation des données sortantes
Note: Supprimer / rendre vide les attributs ayant des valeurs NULL
NullAttributeMapper_6
    ATTRCHOICE = Selected Attributes
    ATTRLIST = annee categorie date mois quart
    NULL_TREATMENT = Null
    OTHER_VALUE = :
    SOURCE_ATTR_VAL = Null
    -> vol_dans_char_2018 (writer POSTGIS_6)

Bookmark: Crime 2023
Note: Sélectionner seulement les données de 2023
Tester_:_2023
    BOOL_OP = OR
    TEST_CLAUSE = CASE_INSENSITIVE_TEST @Value(DATE) BEGINS_WITH 2023
    TEST_MODE = CASE_INSENSITIVE_TEST
    PASSED -> AttributeCreator_2023
Note: Ajoute colonne "annee" avec la valeur "2023"
AttributeCreator_2023
    ATTR_TABLE = SET_TO annee = 2023
    -> Tester_:_Janvier_2023
    -> Tester_:_Fevrier_2023
    -> Tester_:_Mars_2023
    -> Tester_:_Avril_2023
    -> Tester_:_Mai_2023
    -> Tester_:_Juin_2023
    -> Tester_:_Juillet_2023
    -> Tester_:_Aout_2023
    -> Tester_:_Septembre_2023
    -> Tester_:_Octobre_2023
    -> Tester_:_Novembre_2023
    -> Tester_:_Decembre_2023
Note: Sélectionner uniquement les données pour chaque mois
Tester_:_Janvier_2023
    BOOL_OP = COMPOSITE
    COMPOSITE_TEST = 1 AND 2
    TEST_CLAUSE:
      TEST @Value(DATE) >= 20230101
      TEST @Value(DATE) <= 20230131
    TEST_MODE = TEST
    PASSED -> AttributeFilter_Jan2023
Note: Trier les données selon la catégorie d'acte criminel
AttributeFilter_Jan2023
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_janvier2023
Note: - Ajoute la colonne "mois" / - Renomme toutes les colonne en minuscule / - Élimine la colonne "_clipped"
AttributeManager_janvier2023
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = janvier
    USER_EXPOSED_ATTRIBUTES = mois
    -> NullAttributeMapper_2
Tester_:_Fevrier_2023
    BOOL_OP = COMPOSITE
    COMPOSITE_TEST = 1 AND 2
    TEST_CLAUSE:
      TEST @Value(DATE) >= 20230201
      TEST @Value(DATE) <= 20230229
    TEST_MODE = TEST
    PASSED -> AttributeFilter_Fev2023
AttributeFilter_Fev2023
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_fevrier2023
AttributeManager_fevrier2023
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = fevrier
    USER_EXPOSED_ATTRIBUTES = mois
    -> NullAttributeMapper_2
Tester_:_Mars_2023
    BOOL_OP = COMPOSITE
    COMPOSITE_TEST = 1 AND 2
    TEST_CLAUSE:
      TEST @Value(DATE) >= 20230301
      TEST @Value(DATE) <= 20230331
    TEST_MODE = TEST
    PASSED -> AttributeFilter_Mars2023
AttributeFilter_Mars2023
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_mars2023
AttributeManager_mars2023
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = mars
    USER_EXPOSED_ATTRIBUTES = mois
    -> NullAttributeMapper_2
Tester_:_Avril_2023
    BOOL_OP = COMPOSITE
    COMPOSITE_TEST = 1 AND 2
    TEST_CLAUSE:
      TEST @Value(DATE) >= 20230401
      TEST @Value(DATE) <= 20230430
    TEST_MODE = TEST
    PASSED -> AttributeFilter_Avril2023
AttributeFilter_Avril2023
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_avril2023
AttributeManager_avril2023
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = avril
    USER_EXPOSED_ATTRIBUTES = mois
    -> NullAttributeMapper_2
Tester_:_Mai_2023
    BOOL_OP = COMPOSITE
    COMPOSITE_TEST = 1 AND 2
    TEST_CLAUSE:
      TEST @Value(DATE) >= 20230501
      TEST @Value(DATE) <= 20230531
    TEST_MODE = TEST
    PASSED -> AttributeFilter_Mai2023
AttributeFilter_Mai2023
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_mai2023
AttributeManager_mai2023
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = mai
    USER_EXPOSED_ATTRIBUTES = mois
    -> NullAttributeMapper_2
Tester_:_Juin_2023
    BOOL_OP = COMPOSITE
    COMPOSITE_TEST = 1 AND 2
    TEST_CLAUSE:
      TEST @Value(DATE) >= 20230601
      TEST @Value(DATE) <= 20230630
    TEST_MODE = TEST
    PASSED -> AttributeFilter_Juin2023
AttributeFilter_Juin2023
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_juin2023
AttributeManager_juin2023
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = juin
    USER_EXPOSED_ATTRIBUTES = mois
    -> NullAttributeMapper_2
Tester_:_Juillet_2023
    BOOL_OP = COMPOSITE
    COMPOSITE_TEST = 1 AND 2
    TEST_CLAUSE:
      TEST @Value(DATE) >= 20230701
      TEST @Value(DATE) <= 20230731
    TEST_MODE = TEST
    PASSED -> AttributeFilter_Juillet2023
AttributeFilter_Juillet2023
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_juillet2023
AttributeManager_juillet2023
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = juillet
    USER_EXPOSED_ATTRIBUTES = mois
    -> NullAttributeMapper_2
Tester_:_Aout_2023
    BOOL_OP = COMPOSITE
    COMPOSITE_TEST = 1 AND 2
    TEST_CLAUSE:
      TEST @Value(DATE) >= 20230801
      TEST @Value(DATE) <= 20230831
    TEST_MODE = TEST
    PASSED -> AttributeFilter_Aout2023
AttributeFilter_Aout2023
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_aout2023
AttributeManager_aout2023
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = aout
    USER_EXPOSED_ATTRIBUTES = mois
    -> NullAttributeMapper_2
Tester_:_Septembre_2023
    BOOL_OP = COMPOSITE
    COMPOSITE_TEST = 1 AND 2
    TEST_CLAUSE:
      TEST @Value(DATE) >= 20230901
      TEST @Value(DATE) <= 20230930
    TEST_MODE = TEST
    PASSED -> AttributeFilter_Sept2023
AttributeFilter_Sept2023
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_septembre2023
AttributeManager_septembre2023
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = septembre
    USER_EXPOSED_ATTRIBUTES = mois
    -> NullAttributeMapper_2
Tester_:_Octobre_2023
    BOOL_OP = COMPOSITE
    COMPOSITE_TEST = 1 AND 2
    TEST_CLAUSE:
      TEST @Value(DATE) >= 20231001
      TEST @Value(DATE) <= 20231031
    TEST_MODE = TEST
    PASSED -> AttributeFilter_Oct2023
AttributeFilter_Oct2023
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_octobre2023
AttributeManager_octobre2023
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = octobre
    USER_EXPOSED_ATTRIBUTES = mois
    -> NullAttributeMapper_2
Tester_:_Novembre_2023
    BOOL_OP = COMPOSITE
    COMPOSITE_TEST = 1 AND 2
    TEST_CLAUSE:
      TEST @Value(DATE) >= 20231101
      TEST @Value(DATE) <= 20231130
    TEST_MODE = TEST
    PASSED -> AttributeFilter_Nov2023
AttributeFilter_Nov2023
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_novembre2023
AttributeManager_novembre2023
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = novembre
    USER_EXPOSED_ATTRIBUTES = mois
    -> NullAttributeMapper_2
Tester_:_Decembre_2023
    BOOL_OP = COMPOSITE
    COMPOSITE_TEST = 1 AND 2
    TEST_CLAUSE:
      TEST @Value(DATE) >= 20231201
      TEST @Value(DATE) <= 20231231
    TEST_MODE = TEST
    PASSED -> AttributeFilter_Dec2023
AttributeFilter_Dec2023
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_decembre2023
AttributeManager_decembre2023
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = decembre
    USER_EXPOSED_ATTRIBUTES = mois
    -> NullAttributeMapper_2
Note: Exportation vers PostGIS
vol_dans_char_2023 (writer POSTGIS_1)
    attributes: categorie text, date text, quart text, pdq float8, x float8, y float8, longitude float8, latitude float8, _geometry text, mois varchar(200), annee varchar(200)

Bookmark: Validation des données sortantes
Note: Supprimer / rendre vide les attributs ayant des valeurs NULL
NullAttributeMapper_2
    ATTRCHOICE = Selected Attributes
    ATTRLIST = annee categorie date mois quart
    NULL_TREATMENT = Null
    OTHER_VALUE = :
    SOURCE_ATTR_VAL = Null
    -> vol_dans_char_2023 (writer POSTGIS_1)

Bookmark: Crime 2022
Note: Sélectionner seulement les données de 2022
Tester_:_2022
    BOOL_OP = OR
    TEST_CLAUSE = CASE_INSENSITIVE_TEST @Value(DATE) BEGINS_WITH 2022
    TEST_MODE = CASE_INSENSITIVE_TEST
    PASSED -> AttributeCreator_2022
Note: Ajoute colonne "annee" avec la valeur "2022"
AttributeCreator_2022
    ATTR_TABLE = SET_TO annee = 2022
    -> Tester_:_Aout_2022
    -> Tester_:_Juillet_2022
    -> Tester_:_Fevrier_2022
    -> Tester_:_Janvier_2022
    -> Tester_:_Mai_2022
    -> Tester_:_Novembre_2022
    -> Tester_:_Decembre_2022
    -> Tester_:_Septembre_2022
    -> Tester_:_Juin_2022
    -> Tester_:_Octobre_2022
    -> Tester_:_Avril_2022
    -> Tester_:_Mars_2022
Note: Sélectionner seulement les données pour chaque mois
Tester_:_Janvier_2022
    BOOL_OP = COMPOSITE
    COMPOSITE_TEST = 1 AND 2
    TEST_CLAUSE:
      TEST @Value(DATE) >= 20220101
      TEST @Value(DATE) <= 20220131
    TEST_MODE = TEST
    PASSED -> AttributeFilter_Jan2022
Note: Trier les données selon la catégorie d'acte criminel
AttributeFilter_Jan2022
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_janvier2022
Note: - Ajoute la colonne "mois" / - Renomme toutes les colonne en minuscule / - Élimine la colonne "_clipped"
AttributeManager_janvier2022
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = janvier
    USER_EXPOSED_ATTRIBUTES = mois
    -> NullAttributeMapper_3
Tester_:_Fevrier_2022
    BOOL_OP = COMPOSITE
    COMPOSITE_TEST = 1 AND 2
    TEST_CLAUSE:
      TEST @Value(DATE) >= 20220201
      TEST @Value(DATE) <= 20220229
    TEST_MODE = TEST
    PASSED -> AttributeFilter_Fev2022
AttributeFilter_Fev2022
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_fevrier2022
AttributeManager_fevrier2022
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = fevrier
    USER_EXPOSED_ATTRIBUTES = mois
    -> NullAttributeMapper_3
Tester_:_Mars_2022
    BOOL_OP = COMPOSITE
    COMPOSITE_TEST = 1 AND 2
    TEST_CLAUSE:
      TEST @Value(DATE) >= 20220301
      TEST @Value(DATE) <= 20220331
    TEST_MODE = TEST
    PASSED -> AttributeFilter_Mars2022
AttributeFilter_Mars2022
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_mars2022
AttributeManager_mars2022
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = mars
    USER_EXPOSED_ATTRIBUTES = mois
    -> NullAttributeMapper_3
Tester_:_Avril_2022
    BOOL_OP = COMPOSITE
    COMPOSITE_TEST = 1 AND 2
    TEST_CLAUSE:
      TEST @Value(DATE) >= 20220401
      TEST @Value(DATE) <= 20220430
    TEST_MODE = TEST
    PASSED -> AttributeFilter_Avril2022
AttributeFilter_Avril2022
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_avril2022
AttributeManager_avril2022
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = avril
    USER_EXPOSED_ATTRIBUTES = mois
    -> NullAttributeMapper_3
Tester_:_Mai_2022
    BOOL_OP = COMPOSITE
    COMPOSITE_TEST = 1 AND 2
    TEST_CLAUSE:
      TEST @Value(DATE) >= 20220501
      TEST @Value(DATE) <= 20220531
    TEST_MODE = TEST
    PASSED -> AttributeFilter_Mai2022
AttributeFilter_Mai2022
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_mai2022
AttributeManager_mai2022
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = mai
    USER_EXPOSED_ATTRIBUTES = mois
    -> NullAttributeMapper_3
Tester_:_Juin_2022
    BOOL_OP = COMPOSITE
    COMPOSITE_TEST = 1 AND 2
    TEST_CLAUSE:
      TEST @Value(DATE) >= 20220601
      TEST @Value(DATE) <= 20220630
    TEST_MODE = TEST
    PASSED -> AttributeFilter_Juin2022
AttributeFilter_Juin2022
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_juin2022
AttributeManager_juin2022
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = juin
    USER_EXPOSED_ATTRIBUTES = mois
    -> NullAttributeMapper_3
Tester_:_Juillet_2022
    BOOL_OP = COMPOSITE
    COMPOSITE_TEST = 1 AND 2
    TEST_CLAUSE:
      TEST @Value(DATE) >= 20220701
      TEST @Value(DATE) <= 20220731
    TEST_MODE = TEST
    PASSED -> AttributeFilter_Juillet2022
AttributeFilter_Juillet2022
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_juillet2022
AttributeManager_juillet2022
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = juillet
    USER_EXPOSED_ATTRIBUTES = mois
    -> NullAttributeMapper_3
Tester_:_Aout_2022
    BOOL_OP = COMPOSITE
    COMPOSITE_TEST = 1 AND 2
    TEST_CLAUSE:
      TEST @Value(DATE) >= 20220801
      TEST @Value(DATE) <= 20220831
    TEST_MODE = TEST
    PASSED -> AttributeFilter_Aout2022
AttributeFilter_Aout2022
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_aout2022
AttributeManager_aout2022
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = aout
    USER_EXPOSED_ATTRIBUTES = mois
    -> NullAttributeMapper_3
Tester_:_Septembre_2022
    BOOL_OP = COMPOSITE
    COMPOSITE_TEST = 1 AND 2
    TEST_CLAUSE:
      TEST @Value(DATE) >= 20220901
      TEST @Value(DATE) <= 20220930
    TEST_MODE = TEST
    PASSED -> AttributeFilter_Sept2022
AttributeFilter_Sept2022
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_septembre2022
AttributeManager_septembre2022
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = septembre
    USER_EXPOSED_ATTRIBUTES = mois
    -> NullAttributeMapper_3
Tester_:_Octobre_2022
    BOOL_OP = COMPOSITE
    COMPOSITE_TEST = 1 AND 2
    TEST_CLAUSE:
      TEST @Value(DATE) >= 20221001
      TEST @Value(DATE) <= 20221031
    TEST_MODE = TEST
    PASSED -> AttributeFilter_Oct2022
AttributeFilter_Oct2022
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_octobre2022
AttributeManager_octobre2022
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = octobre
    USER_EXPOSED_ATTRIBUTES = mois
    -> NullAttributeMapper_3
Tester_:_Novembre_2022
    BOOL_OP = COMPOSITE
    COMPOSITE_TEST = 1 AND 2
    TEST_CLAUSE:
      TEST @Value(DATE) >= 20221101
      TEST @Value(DATE) <= 20221130
    TEST_MODE = TEST
    PASSED -> AttributeFilter_Nov2022
AttributeFilter_Nov2022
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_novembre2022
AttributeManager_novembre2022
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = novembre
    USER_EXPOSED_ATTRIBUTES = mois
    -> NullAttributeMapper_3
Tester_:_Decembre_2022
    BOOL_OP = COMPOSITE
    COMPOSITE_TEST = 1 AND 2
    TEST_CLAUSE:
      TEST @Value(DATE) >= 20221201
      TEST @Value(DATE) <= 20221231
    TEST_MODE = TEST
    PASSED -> AttributeFilter_Dec2022
AttributeFilter_Dec2022
    ATTR_NAME = CATEGORIE
    ATTR_VALUES = <Empty>,<Missing>,<Null>,<Unfiltered>,Infractions entrainant la mort,Introduction,Méfait,Vol dans / sur véhicule à moteur,Vol de véhicule à moteur,Vols qualifiés
    Vol dans / sur véhicule à moteur -> AttributeManager_decembre2022
AttributeManager_decembre2022
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      REMOVE _clipped
      SET_TO mois = decembre
    USER_EXPOSED_ATTRIBUTES = mois
    -> NullAttributeMapper_3
Note: Exportation vers PostGIS
vol_dans_char_2022 (writer POSTGIS_2)
    attributes: categorie text, date text, quart text, pdq float8, x float8, y float8, longitude float8, latitude float8, _geometry text, mois varchar(200), annee varchar(200)

Bookmark: Validation des données sortantes
Note: Supprimer / rendre vide les attributs ayant des valeurs NULL
NullAttributeMapper_3
    ATTRCHOICE = Selected Attributes
    ATTRLIST = annee categorie date mois quart
    NULL_TREATMENT = Null
    OTHER_VALUE = :
    SOURCE_ATTR_VAL = Null
    -> vol_dans_char_2022 (writer POSTGIS_2)

Bookmark: LiDAR 2015
LAS (reader LAS_2)
    -> NullAttributeMapper_14
PointCloudThinner_3
    INTERVAL = 30
    THINNED -> PointCloudCombiner
    <REJECTED> -> PointCloudThinner_3__Rejected_
PointCloudThinner_3__Rejected_: Logger
    LOG_FEATURE = LOG_ONLY
    MAXCOORDS = 20
    MAXFEATS = 20
    MESSAGE = Feature is:
    SEVERITY = INFO
LAS (reader LAS_1)
    -> NullAttributeMapper_15
PointCloudThinner_4
    INTERVAL = 30
    THINNED -> PointCloudCombiner
    <REJECTED> -> PointCloudThinner_4__Rejected_
PointCloudThinner_4__Rejected_: Logger
    LOG_FEATURE = LOG_ONLY
    MAXCOORDS = 20
    MAXFEATS = 20
    MESSAGE = Feature is:
    SEVERITY = INFO
Note: Importation depuis un lien url des données LAS de LIDAR 2015 / --> Disponible sur le site des données ouvertes de Montréal
LAS (reader LAS_3)
    -> NullAttributeMapper_13
Note: Nettoyage des données LiDAR - / - réduire de 30 fois le nombre de points, car beaucoup de redondance non-nécessaire
PointCloudThinner_2
    INTERVAL = 30
    THINNED -> PointCloudCombiner
    <REJECTED> -> PointCloudThinner_2__Rejected_
PointCloudThinner_2__Rejected_: Logger
    LOG_FEATURE = LOG_ONLY
    MAXCOORDS = 20
    MAXFEATS = 20
    MESSAGE = Feature is:
    SEVERITY = INFO
Note: Combiner les données LiDAR - / - fusionner les 9 différents nuages de points en un seul
PointCloudCombiner
    ACCUM_ATTRS_NAME = Yes
    EXTRACT_RASTER_NODATA_NAME = No
    SPACING = 1.0
    -> EsriReprojector
    <REJECTED> -> PointCloudCombiner__Rejected_
PointCloudCombiner__Rejected_: Logger
    LOG_FEATURE = LOG_ONLY
    MAXCOORDS = 20
    MAXFEATS = 20
    MESSAGE = Feature is:
    SEVERITY = INFO
EsriReprojector
    DEST = ESRIWKT|WGS_1984_Web_Mercator_Auxiliary_Sphere|PROJCS["WGS_1984_Web_Mercator_Auxiliary_Sphere",GEOGCS["GCS_WGS_1984",DATUM["D_WGS_1984",SPHEROID["WGS_1984",6378137.0,298.257223563]],PRIMEM["Greenwich",0.0],UNIT["Degree",0.0174532925199433]],PROJECTION["Mercator_Auxiliary_Sphere"],PARAMETER["False_Easting",0.0],PARAMETER["False_Northing",0.0],PARAMETER["Central_Meridian",0.0],PARAMETER["Standard_Parallel_1",0.0],PARAMETER["Auxiliary_Sphere_Type",0.0],UNIT["Meter",1.0]]
    GEOTRANSFORMATION_DIRECTION = Forward
    GEOTRANSFORMATION_NAME = NAD_1983_CSRS_To_WGS_1984
    INTERPOLATION_TYPE_NAME = Nearest Neighbor
    RASTER_CELL_SIZE = Preserve Cells
    RASTER_TOLERANCE = 0.0
    SOURCE = ESRIWKT|NAD_1983_CSRS_MTM_8|PROJCS["NAD_1983_CSRS_MTM_8",GEOGCS["GCS_North_American_1983_CSRS",DATUM["D_North_American_1983_CSRS",SPHEROID["GRS_1980",6378137.0,298.257222101]],PRIMEM["Greenwich",0.0],UNIT["Degree",0.0174532925199433]],PROJECTION["Transverse_Mercator"],PARAMETER["False_Easting",304800.0],PARAMETER["False_Northing",0.0],PARAMETER["Central_Meridian",-73.5],PARAMETER["Scale_Factor",0.9999],PARAMETER["Latitude_Of_Origin",0.0],UNIT["Meter",1.0]]
    REPROJECTED -> Reprojector_11
Note: Reprojette les données en 3857
Reprojector_11
    DEST = EPSG:3857
    INTERPOLATION_TYPE_NAME = Nearest Neighbor
    RASTER_CELL_SIZE = Preserve Cells
    RASTER_TOLERANCE = 0.0
    REPROJECTED -> Clipper_2 [CLIPPEE]

Bookmark: Validation des données entrantes
NullAttributeMapper_14
    ATTRCHOICE = All Attributes
    NULL_TREATMENT = Null
    OTHER_VALUE = :
    SOURCE_ATTR_VAL = Null
    -> PointCloudThinner_3
NullAttributeMapper_15
    ATTRCHOICE = All Attributes
    NULL_TREATMENT = Null
    OTHER_VALUE = :
    SOURCE_ATTR_VAL = Null
    -> PointCloudThinner_4
Note: Supprimer / rendre vide les attributs ayant des valeurs NULL
NullAttributeMapper_13
    ATTRCHOICE = All Attributes
    NULL_TREATMENT = Null
    OTHER_VALUE = :
    SOURCE_ATTR_VAL = Null
    -> PointCloudThinner_2

Bookmark: Découpe et simplifie les nuages de points combinés selon la limite de l'arrondissement Ville-Marie
Note: Découpe le nuage de point avec les limite de l'arrondissement Ville-Marie
Clipper_2
    ATTR_ACCUM_MODE = Merge Clipper
    ATTR_CONFLICT_RES = Use Clippee
    BOUNDARY_CASES = Treat as Inside
    CLEANING_TOLERANCE = Automatic
    CLIPPED_ATTR = _clipped
    CLIP_TYPE = Multiple Clippers
    CONNECT_Z_MODE = First Wins
    LINES_AS_SEGMENTS = No
    MEASURE_TYPE = Continuous
    MISSING_VAL_MODE = Compute
    PRESERVE_CLIPPEE_EXTENTS = No
    VAL_SOURCE = Clippee Only
    INSIDE -> PointCloudSimplifier
    <REJECTED> -> Clipper__Rejected_
Note: Processus très lourd : Réduit la densité de points tout en préservant l'information importante et la précision de l'image
Note: - Rejette géométries corrompues / dégradées
PointCloudSimplifier
    MASB_BISECT_K = 2
    MASB_BISECT_T = 1.0
    MASB_CELLSIZE = Auto
    MASB_D_PLANAR_T = 32.0
    MASB_D_PRESERVE_T = 20.0
    MASB_EPSILON = 0.5
    MASB_INTERIOR = Use Interior and Exterior MAT
    MASB_IR = Auto
    MASB_K = 10
    MASB_MAX_DENSITY = None
    MASB_MIN_DENSITY = None
    MASB_SQUARED = Linear
    SIMPLIFIER_TYPE_DISPLAY = Medial Axis Transform
    SIMPLIFIED -> GeometryValidator_4
    <REJECTED> -> PointCloudSimplifier__Rejected_
Note: Enregistre la donnée sur mon ordinateur afin de ne pas devoir faire rouler toutes ces étapes pour obtenir ce même LiDAR
lidar_simplifier (writer LAS_5)
PointCloudSimplifier__Rejected_: Logger
    LOG_FEATURE = LOG_ONLY
    MAXCOORDS = 20
    MAXFEATS = 20
    MESSAGE = Feature is:
    SEVERITY = INFO
Clipper__Rejected_: Logger
    LOG_FEATURE = LOG_ONLY
    MAXCOORDS = 20
    MAXFEATS = 20
    MESSAGE = Feature is:
    SEVERITY = INFO

Bookmark: Validation des données sortantes
GeometryValidator_4
    ISSUE_ATTR_NAME = _issues
    PRESETS = Custom
    REPAIR = Yes
    RULES = NAN_REMOVAL PROCESS_MEASURE]NO]FME_CONTROLLER_QUERY_FILE]transformers/dependencies/geometryvalidator8/NAN_REMOVAL.fme]FME_CONTROLLER_CHOICE]NAN_REMOVAL TYPE_REPAIR CONNECT_Z_MODE]FIRST_WINS]ARC_ENDPOINT_TOLERANCE_MODE]Auto]ARC_ENDPOINT_TOLERANCE]<Unused>]FME_CONTROLLER_QUERY_FILE]transformers/dependencies/geometryvalidator8/TYPE_REPAIR.fme]FME_CONTROLLER_CHOICE]TYPE_REPAIR
    SUMMARY = Detailed
    PASSED -> lidar_simplifier (writer LAS_5)

Bookmark: Association des couleurs du raster vers les nuages points combinés
Note: lidar_simplifier : préalablement exporter vers PostGIS
LAS (reader LAS_4)
    -> NullAttributeMapper_10
Note: Reprojette les données en 3857
Reprojector_10
    DEST = EPSG:3857
    INTERPOLATION_TYPE_NAME = Nearest Neighbor
    RASTER_CELL_SIZE = Preserve Cells
    RASTER_TOLERANCE = 0.0
    REPROJECTED -> PointCloudOnRasterComponentSetter [PointCloud]
Note: image_aerienne_2002_resample : préalablement exporter vers PostGIS
image_aerienne_2002_resample (reader POSTGIS_RASTER_1)
    -> NullAttributeMapper_11
Note: Reprojette les données en 3857
Reprojector_12
    DEST = EPSG:3857
    INTERPOLATION_TYPE_NAME = Nearest Neighbor
    RASTER_CELL_SIZE = Preserve Cells
    RASTER_TOLERANCE = 0.0
    REPROJECTED -> PointCloudOnRasterComponentSetter [Raster]
Note: Ajoutez de la couleur au nuage de point / - Ceci est possible en ajoutant les valeur du raster (bandes rouges, vertes et bleus)
PointCloudOnRasterComponentSetter
    COMPONENT_SPECIFICATION = Color
    DEFAULT_VALUES_OVERWRITE_DATA = No
    EXTRACT_NODATA = No
    INTERPOLATION = Nearest Neighbor
    PointCloud -> PointCloudCombiner_2
    <REJECTED> -> PointCloudOnRasterComponentSetter__Rejected_
PointCloudCombiner_2
    ACCUM_ATTRS_NAME = Yes
    EXTRACT_RASTER_NODATA_NAME = No
    SPACING = 1.0
    -> PointCloudFilter
    <REJECTED> -> PointCloudCombiner_2__Rejected_
Note: Filtrer les valeurs du nuage de points / - Permet de rejeter les valeurs ayant "0" dans RGB
PointCloudFilter
    FILTER_TABLE = @Component(color_red)!=0&&@Component(color_blue)!=0&&@Component(color_green) @Component(color_red)!=0&&@Component(color_blue)!=0&&@Component(color_green)
    OUTPUT_UNFILTERED_POINTS = Yes
    @Component(color_red)!=0&&@Component(color_blue)!=0&&@Component(color_green) -> BoundingBoxAccumulator
    @Component(color_red)!=0&&@Component(color_blue)!=0&&@Component(color_green) -> PointCloudCoercer
    <REJECTED> -> PointCloudFilter__Rejected_
Note: Transformer nuage de points vers point (vecteur) / Il faut s'assurer de choisir les composantes suivantes : z, color_red, color_green, color_blue
PointCloudCoercer
    ACCUM_ATTRS_NAME = Yes
    CONVERT_TO_DISPLAY = Individual Points
    PART_NUMBER_ATTR_NAME = _part_number
    POINT_COMPONENTS = normal_z color_red color_green color_blue
    POINT_COMPONENTS_PRESERVE_DISPLAY = Attributes
    COERCED -> PointOnAreaOverlayer [POINT]
    <REJECTED> -> PointCloudToPointCoercer__Rejected_
PointCloudToPointCoercer__Rejected_: Logger
    LOG_FEATURE = LOG_ONLY
    MAXCOORDS = 20
    MAXFEATS = 20
    MESSAGE = Feature is:
    SEVERITY = INFO
PointCloudFilter__Rejected_: Logger
    LOG_FEATURE = LOG_ONLY
    MAXCOORDS = 20
    MAXFEATS = 20
    MESSAGE = Feature is:
    SEVERITY = INFO
PointCloudCombiner_2__Rejected_: Logger
    LOG_FEATURE = LOG_ONLY
    MAXCOORDS = 20
    MAXFEATS = 20
    MESSAGE = Feature is:
    SEVERITY = INFO
PointCloudOnRasterComponentSetter__Rejected_: Logger
    LOG_FEATURE = LOG_ONLY
    MAXCOORDS = 20
    MAXFEATS = 20
    MESSAGE = Feature is:
    SEVERITY = INFO

Bookmark: Validation des données entrantes
Note: Supprimer / rendre vide les attributs ayant des valeurs NULL
NullAttributeMapper_10
    ATTRCHOICE = All Attributes
    NULL_TREATMENT = Null
    OTHER_VALUE = :
    SOURCE_ATTR_VAL = Null
    -> Reprojector_10
Note: Supprimer / rendre vide les attributs ayant des valeurs NULL
NullAttributeMapper_11
    ATTRCHOICE = All Attributes
    NULL_TREATMENT = Null
    OTHER_VALUE = :
    SOURCE_ATTR_VAL = Null
    -> Reprojector_12

Bookmark: Créer un bounding box
Note: Permet de découper les empreintes de batiments
BoundingBoxAccumulator
    ACCUM_ATTRS_NAME = Use Attributes From One Feature
    BOUNDING_BOX -> Clipper_4 [CLIPPER]
    BOUNDING_BOX -> Clipper_3 [CLIPPER]
    <REJECTED> -> BoundingBoxAccumulator__Rejected_
BoundingBoxAccumulator__Rejected_: Logger
    LOG_FEATURE = LOG_ONLY
    MAXCOORDS = 20
    MAXFEATS = 20
    MESSAGE = Feature is:
    SEVERITY = INFO

Bookmark: Importation et trie : Empruntes des toits (Polygone)
Note: Importation depuis un lien url des données SHP d'empruntes des toits (polygone) / --> Disponible sur le site des données ouvertes de Montréal
CARTO-BAT-TOIT (reader SHAPEFILE_1)
    attributes: calque varchar(200), projection varchar(200), reference varchar(200), EQM_plani varchar(200), EQM_alti varchar(200), MAJ varchar(200), methode varchar(200), source varchar(200), producteur varchar(200), superficie varchar(200), version varchar(200)
    -> NullAttributeMapper_16
EsriReprojector_3
    DEST = ESRIWKT|WGS_1984_Web_Mercator_Auxiliary_Sphere|PROJCS["WGS_1984_Web_Mercator_Auxiliary_Sphere",GEOGCS["GCS_WGS_1984",DATUM["D_WGS_1984",SPHEROID["WGS_1984",6378137.0,298.257223563]],PRIMEM["Greenwich",0.0],UNIT["Degree",0.0174532925199433]],PROJECTION["Mercator_Auxiliary_Sphere"],PARAMETER["False_Easting",0.0],PARAMETER["False_Northing",0.0],PARAMETER["Central_Meridian",0.0],PARAMETER["Standard_Parallel_1",0.0],PARAMETER["Auxiliary_Sphere_Type",0.0],UNIT["Meter",1.0]]
    GEOTRANSFORMATION_DIRECTION = Forward
    GEOTRANSFORMATION_NAME = NAD_1983_CSRS_To_WGS_1984
    INTERPOLATION_TYPE_NAME = Nearest Neighbor
    RASTER_CELL_SIZE = Preserve Cells
    RASTER_TOLERANCE = 0.0
    SOURCE = ESRIWKT|NAD_1983_CSRS_MTM_8|PROJCS["NAD_1983_CSRS_MTM_8",GEOGCS["GCS_North_American_1983_CSRS",DATUM["D_North_American_1983_CSRS",SPHEROID["GRS_1980",6378137.0,298.257222101]],PRIMEM["Greenwich",0.0],UNIT["Degree",0.0174532925199433]],PROJECTION["Transverse_Mercator"],PARAMETER["False_Easting",304800.0],PARAMETER["False_Northing",0.0],PARAMETER["Central_Meridian",-73.5],PARAMETER["Scale_Factor",0.9999],PARAMETER["Latitude_Of_Origin",0.0],UNIT["Meter",1.0]]
    REPROJECTED -> Reprojector_13
Note: Reprojette les données en 3857
Reprojector_13
    DEST = EPSG:3857
    INTERPOLATION_TYPE_NAME = Nearest Neighbor
    RASTER_CELL_SIZE = Preserve Cells
    RASTER_TOLERANCE = 0.0
    REPROJECTED -> Clipper_4 [CLIPPEE]
Note: Découpe les empruntes de toits avec le ''BoundingBox'' du LAS
Clipper_4
    ATTR_ACCUM_MODE = Merge Clipper
    ATTR_CONFLICT_RES = Use Clippee
    BOUNDARY_CASES = Treat as Inside
    CLEANING_TOLERANCE = Automatic
    CLIPPED_ATTR = _clipped
    CLIP_TYPE = Multiple Clippers
    CONNECT_Z_MODE = First Wins
    LINES_AS_SEGMENTS = No
    MEASURE_TYPE = Continuous
    MISSING_VAL_MODE = Compute
    PRESERVE_CLIPPEE_EXTENTS = No
    VAL_SOURCE = Clippee Only
    INSIDE -> PolygonCutter [Polygons]
    <REJECTED> -> Clipper_3__Rejected_
Clipper_3__Rejected_: Logger
    LOG_FEATURE = LOG_ONLY
    MAXCOORDS = 20
    MAXFEATS = 20
    MESSAGE = Feature is:
    SEVERITY = INFO

Bookmark: Validation des données entrantes
Note: Supprimer / rendre vide les attributs ayant des valeurs NULL
NullAttributeMapper_16
    ATTRCHOICE = All Attributes
    NULL_TREATMENT = Null
    OTHER_VALUE = :
    SOURCE_ATTR_VAL = Null
    -> EsriReprojector_3

Bookmark: Importation et trie : Détail des toits (Ligne)
Note: Importation depuis un lien url des données SHP de détails des toits (ligne) / --> Disponible sur le site des données ouvertes de Montréal
CARTO-BAT-DETAIL (reader SHAPEFILE_1)
    attributes: calque varchar(200), projection varchar(200), reference varchar(200), EQM_plani varchar(200), EQM_alti varchar(200), MAJ varchar(200), methode varchar(200), source varchar(200), producteur varchar(200), longueur varchar(200), version varchar(200)
    -> NullAttributeMapper_17
EsriReprojector_2
    DEST = ESRIWKT|WGS_1984_Web_Mercator_Auxiliary_Sphere|PROJCS["WGS_1984_Web_Mercator_Auxiliary_Sphere",GEOGCS["GCS_WGS_1984",DATUM["D_WGS_1984",SPHEROID["WGS_1984",6378137.0,298.257223563]],PRIMEM["Greenwich",0.0],UNIT["Degree",0.0174532925199433]],PROJECTION["Mercator_Auxiliary_Sphere"],PARAMETER["False_Easting",0.0],PARAMETER["False_Northing",0.0],PARAMETER["Central_Meridian",0.0],PARAMETER["Standard_Parallel_1",0.0],PARAMETER["Auxiliary_Sphere_Type",0.0],UNIT["Meter",1.0]]
    GEOTRANSFORMATION_DIRECTION = Forward
    GEOTRANSFORMATION_NAME = NAD_1983_CSRS_To_WGS_1984
    INTERPOLATION_TYPE_NAME = Nearest Neighbor
    RASTER_CELL_SIZE = Preserve Cells
    RASTER_TOLERANCE = 0.0
    SOURCE = ESRIWKT|NAD_1983_CSRS_MTM_8|PROJCS["NAD_1983_CSRS_MTM_8",GEOGCS["GCS_North_American_1983_CSRS",DATUM["D_North_American_1983_CSRS",SPHEROID["GRS_1980",6378137.0,298.257222101]],PRIMEM["Greenwich",0.0],UNIT["Degree",0.0174532925199433]],PROJECTION["Transverse_Mercator"],PARAMETER["False_Easting",304800.0],PARAMETER["False_Northing",0.0],PARAMETER["Central_Meridian",-73.5],PARAMETER["Scale_Factor",0.9999],PARAMETER["Latitude_Of_Origin",0.0],UNIT["Meter",1.0]]
    REPROJECTED -> Reprojector_9
Note: Reprojette les données en 3857
Reprojector_9
    DEST = EPSG:3857
    INTERPOLATION_TYPE_NAME = Nearest Neighbor
    RASTER_CELL_SIZE = Preserve Cells
    RASTER_TOLERANCE = 0.0
    REPROJECTED -> Clipper_3 [CLIPPEE]
Note: Découpe les détails de toits avec le ''BoundingBox'' du LAS
Clipper_3
    ATTR_ACCUM_MODE = Merge Clipper
    ATTR_CONFLICT_RES = Use Clippee
    BOUNDARY_CASES = Treat as Inside
    CLEANING_TOLERANCE = Automatic
    CLIPPED_ATTR = _clipped
    CLIP_TYPE = Multiple Clippers
    CONNECT_Z_MODE = First Wins
    LINES_AS_SEGMENTS = No
    MEASURE_TYPE = Continuous
    MISSING_VAL_MODE = Compute
    PRESERVE_CLIPPEE_EXTENTS = No
    VAL_SOURCE = Clippee Only
    INSIDE -> PolygonCutter [Lines]
    <REJECTED> -> Clipper_2__Rejected_
Clipper_2__Rejected_: Logger
    LOG_FEATURE = LOG_ONLY
    MAXCOORDS = 20
    MAXFEATS = 20
    MESSAGE = Feature is:
    SEVERITY = INFO

Bookmark: Validation des données entrantes
Note: Supprimer / rendre vide les attributs ayant des valeurs NULL
NullAttributeMapper_17
    ATTRCHOICE = All Attributes
    NULL_TREATMENT = Null
    OTHER_VALUE = :
    SOURCE_ATTR_VAL = Null
    -> EsriReprojector_2

Bookmark: Découpe les empruntes de toits avec le détails des toits
Note: Découpe les empreintes de toits avec les détails de toits
PolygonCutter
    DONUTHOLES = Yes
    SNAP_TOLERANCE = 0.001
    Cut -> PointOnAreaOverlayer [AREA]

Bookmark: Jointure spatiale des points et des batiments, calcul du z moyen pour chacune des surfaces de toit et exposition des propriétés pour créer des polygones cartographiables
Note: Jointure spatiale / - Joint les propriétés du / nuage de points (z, couleurs) vers les polygones de batiments
PointOnAreaOverlayer
    CANDIDATE_LIST_ATTRS_TO_INCLUDE_MODE = All Attributes
    CANDIDATE_LIST_NAME = z_accumulation
    DEAGGREGATE_INPUT = Yes
    OV_ATTR = _overlaps
    POLYS_FIRST = YES
    AREA -> ListSummer
    <REJECTED> -> PointOnAreaOverlayer__Rejected_
Note: Regrouper les valeurs en une seule liste
ListSummer
    RESULT = _sum
    SRC_LIST = z_accumulation{}.normal_z
    -> AttributeCreator
Note: Créer un attribut pour calculer la moyenne
AttributeCreator
    ATTR_TABLE = SET_TO z = @Evaluate(@round(@Value(_sum)/@Value(_overlaps),4))
    -> AttributeKeeper
Note: Conserve seulement : / - z / - z_accumulation{1}.fme_color
AttributeKeeper
    CREATE_BULK_MODE_FEATURES = NO
    KEEP_ATTRS = z,z_accumulation{1}.fme_color
    -> ColorConverter
Note: Convertir / de FME-Color / vers WebColor
ColorConverter
    InputAttribute = z_accumulation{1}.fme_color
    InputModel = FME
    OutputModel = Web RGB
    -> GeometryValidator_3
Note: Exportation vers PostGIS
batiment_couleur (writer POSTGIS_10)
    attributes: _output_red varchar(200), _output_green varchar(200), _output_blue varchar(200), _output_color varchar(200), z varchar(200), z_accumulation{}_fme_color varchar(200), _output_key varchar(200), _output_cyan varchar(200), _output_magenta varchar(200), _output_yellow varchar(200)
PointOnAreaOverlayer__Rejected_: Logger
    LOG_FEATURE = LOG_ONLY
    MAXCOORDS = 20
    MAXFEATS = 20
    MESSAGE = Feature is:
    SEVERITY = INFO

Bookmark: Validation des données sortantes
Note: - Rejette géométries corrompues / dégradées
GeometryValidator_3
    ISSUE_ATTR_NAME = _issues
    PRESETS = Custom
    REPAIR = Yes
    RULES = NAN_REMOVAL PROCESS_MEASURE]NO]FME_CONTROLLER_QUERY_FILE]transformers/dependencies/geometryvalidator8/NAN_REMOVAL.fme]FME_CONTROLLER_CHOICE]NAN_REMOVAL TYPE_REPAIR CONNECT_Z_MODE]FIRST_WINS]ARC_ENDPOINT_TOLERANCE_MODE]Auto]ARC_ENDPOINT_TOLERANCE]<Unused>]FME_CONTROLLER_QUERY_FILE]transformers/dependencies/geometryvalidator8/TYPE_REPAIR.fme]FME_CONTROLLER_CHOICE]TYPE_REPAIR
    SUMMARY = Detailed
    PASSED -> batiment_couleur (writer POSTGIS_10)
    <REJECTED> -> GeometryValidator_3__Rejected_
GeometryValidator_3__Rejected_: Logger
    LOG_FEATURE = LOG_ONLY
    MAXCOORDS = 20
    MAXFEATS = 20
    MESSAGE = Feature is:
    SEVERITY = INFO

FME custom transformer ColorConverter
Converts color values between different formats (FME
 RGB
 Web RGB and CMYK)
Input:
1 attribute containing a color triplet in either FME, RGB, Web RGB or CMYK format, comma-separated
Output:
Attributes _output_color (full color triplet in the required format), _output_red, output_green and _output_blue
Supported color models:
FME color, RGB values in range 0..1
RGB values in range 0..255
Web RGB values, a hexadecimal string of 6 characters containing an RGB triplet with each value in the range 00..FF
CMYK values in range 0..1 and 0..100
Note that due to rounding errors the resulting colors might be a bit off. Especially any conversions between the RGB and CMYK color spaces might yield results that differ from other applications (since the RGB and CMYK color spaces are slightly different)

Parameters:
- InputAttribute =
- InputModel =
- OutputModel =

Input (input)
    -> TestFilter
Note: Select input color model
TestFilter
    DEFAULT_VALUE = <UNFILTERED>
    TEST_LIST = BOOL_OP,OR,COMPOSITE_TEST,<Unused>,TEST_CLAUSE,"TEST $(InputModel) = FME",FME,BOOL_OP,OR,COMPOSITE_TEST,<Unused>,TEST_CLAUSE,"TEST $(InputModel) = RGB",RGB,BOOL_OP,OR,COMPOSITE_TEST,<Unused>,TEST_CLAUSE,"TEST $(InputModel) = Web RGB",Web RGB,BOOL_OP,OR,COMPOSITE_TEST,<Unused>,TEST_CLAUSE,"TEST $(InputModel) = CMYK (0..100)",CMYK (0..100),BOOL_OP,OR,COMPOSITE_TEST,<Unused>,TEST_CLAUSE,"TEST $(InputModel) = CMYK (0..1)",CMYK (0..1)
    FME -> AttributeSplitter
    RGB -> AttributeSplitter_2
    Web RGB -> StringReplacer
    CMYK (0..100) -> AttributeSplitter_5
    CMYK (0..1) -> AttributeSplitter_4
Note: Select output color model
TestFilter_2
    DEFAULT_VALUE = <UNFILTERED>
    TEST_LIST = BOOL_OP,OR,COMPOSITE_TEST,<Unused>,TEST_CLAUSE,"TEST $(OutputModel) = FME",FME,BOOL_OP,OR,COMPOSITE_TEST,<Unused>,TEST_CLAUSE,"TEST $(OutputModel) = RGB",RGB,BOOL_OP,OR,COMPOSITE_TEST,<Unused>,TEST_CLAUSE,"TEST $(OutputModel) = Web RGB",Web RGB,BOOL_OP,OR,COMPOSITE_TEST,<Unused>,TEST_CLAUSE,"TEST $(OutputModel) = CMYK (0..1)",CMYK (0..1),BOOL_OP,OR,COMPOSITE_TEST,<Unused>,TEST_CLAUSE,"TEST $(OutputModel) = CMYK (0..100)",CMYK (0..100)
    FME -> AttributeManager_5
    RGB -> AttributeManager_2
    Web RGB -> AttributeManager_7
    CMYK (0..1) -> AttributeManager_10
    CMYK (0..100) -> AttributeManager_11
Output (output)

Bookmark: FME color triplet
AttributeSplitter
    ATTR_NAME = $(InputAttribute)
    DELIMITER = ,
    DROP_EMPTY_PARTS = No
    LIST_NAME = _list
    TRIM_OPTION = Both
    -> AttributeManager
AttributeManager
    ATTR_TABLE:
      SET_TO _input_red = @Value(_list{0})
      SET_TO _input_green = @Value(_list{1})
      SET_TO _input_blue = @Value(_list{2})
    -> TestFilter_2

Bookmark: RGB color triplet
AttributeSplitter_2
    ATTR_NAME = $(InputAttribute)
    DELIMITER = ,
    DROP_EMPTY_PARTS = No
    LIST_NAME = _list
    TRIM_OPTION = Both
    -> AttributeManager_3
AttributeManager_3
    ATTR_TABLE:
      SET_TO _input_red = @Evaluate(@Value(_list{0})/255)
      SET_TO _input_green = @Evaluate(@Value(_list{1})/255)
      SET_TO _input_blue = @Evaluate(@Value(_list{2})/255)
    -> TestFilter_2

Bookmark: Web RGB (hexadecimal)
StringReplacer
    CASE = NO
    FIND_TEXT = ^#
    NO_MATCH = _FME_NO_OP_
    REGEXP = YES
    SRC_ATTRS = $(InputAttribute)
    -> AttributeSplitter_3
AttributeSplitter_3
    ATTR_NAME = $(InputAttribute)
    DELIMITER = 2s2s2s
    DROP_EMPTY_PARTS = No
    LIST_NAME = _list
    TRIM_OPTION = Both
    -> BaseConverter
BaseConverter
    DBASE = 10
    OBASE = 16
    SRC = _list{0}
    VAL_ATTR = _input_red
    WIDTH = 3
    -> BaseConverter_2
BaseConverter_2
    DBASE = 10
    OBASE = 16
    SRC = _list{1}
    VAL_ATTR = _input_green
    WIDTH = 3
    -> BaseConverter_3
BaseConverter_3
    DBASE = 10
    OBASE = 16
    SRC = _list{2}
    VAL_ATTR = _input_blue
    WIDTH = 3
    -> AttributeManager_4
AttributeManager_4
    ATTR_TABLE:
      SET_TO _input_red = @Evaluate(@Value(_input_red)/255)
      SET_TO _input_green = @Evaluate(@Value(_input_green)/255)
      SET_TO _input_blue = @Evaluate(@Value(_input_blue)/255)
    -> TestFilter_2

Bookmark: CMYK
AttributeSplitter_5
    ATTR_NAME = $(InputAttribute)
    DELIMITER = ,
    DROP_EMPTY_PARTS = No
    LIST_NAME = _list
    TRIM_OPTION = Both
    -> AttributeManager_9
AttributeManager_9
    ATTR_TABLE:
      SET_TO _input_red = @Evaluate((1-(@Value(_list{0})/100))*(1-(@Value(_list{3})/100)))
      SET_TO _input_green = @Evaluate((1-(@Value(_list{1})/100))*(1-(@Value(_list{3})/100)))
      SET_TO _input_blue = @Evaluate((1-(@Value(_list{2})/100))*(1-(@Value(_list{3})/100)))
    -> TestFilter_2
AttributeSplitter_4
    ATTR_NAME = $(InputAttribute)
    DELIMITER = ,
    DROP_EMPTY_PARTS = No
    LIST_NAME = _list
    TRIM_OPTION = Both
    -> AttributeManager_8
AttributeManager_8
    ATTR_TABLE:
      SET_TO _input_red = @Evaluate((1-@Value(_list{0}))*(1-@Value(_list{3})))
      SET_TO _input_green = @Evaluate((1-@Value(_list{1}))*(1-@Value(_list{3})))
      SET_TO _input_blue = @Evaluate((1-@Value(_list{2}))*(1-@Value(_list{3})))
    -> TestFilter_2

Bookmark: FME color triplet
AttributeManager_5
    ATTR_TABLE:
      RENAME_SET_VALUE _input_red > _output_red
      RENAME_SET_VALUE _input_green > _output_green
      RENAME_SET_VALUE _input_blue > _output_blue
      SET_TO _output_color = @Value(_output_red),@Value(_output_green),@Value(_output_blue)
    -> Output (output)

Bookmark: RGB color triplet
AttributeManager_2
    ATTR_TABLE:
      SET_TO _output_red = @Evaluate(@int(@Value(_input_red)*255))
      SET_TO _output_green = @Evaluate(@int(@Value(_input_green)*255))
      SET_TO _output_blue = @Evaluate(@int(@Value(_input_blue)*255))
      SET_TO _output_color = @Value(_output_red),@Value(_output_green),@Value(_output_blue)
    -> Output (output)

Bookmark: Web RGB (hexadecimal
AttributeManager_7
    ATTR_TABLE:
      SET_TO _input_red = @Evaluate(int(@Value(_input_red)*255))
      SET_TO _input_green = @Evaluate(int(@Value(_input_green)*255))
      SET_TO _input_blue = @Evaluate(int(@Value(_input_blue)*255))
    -> BaseConverter_4
    -> AttributeManager_7_Output
BaseConverter_4
    DBASE = 16
    OBASE = 10
    SRC = _input_red
    VAL_ATTR = _output_red
    WIDTH = 2
    -> BaseConverter_5
BaseConverter_5
    DBASE = 16
    OBASE = 10
    SRC = _input_green
    VAL_ATTR = _output_green
    WIDTH = 2
    -> BaseConverter_6
BaseConverter_6
    DBASE = 16
    OBASE = 10
    SRC = _input_blue
    VAL_ATTR = _output_blue
    WIDTH = 2
    -> AttributeManager_6
AttributeManager_6
    ATTR_TABLE = SET_TO _output_color = #@Value(_output_red)@Value(_output_green)@Value(_output_blue)
    -> Output (output)
AttributeManager_7_Output: Inspector

Bookmark: CMYK
AttributeManager_10
    ATTR_TABLE:
      SET_TO _output_key = @Evaluate(1-@max(@Value(_input_red),@Value(_input_green),@Value(_input_blue)))
      SET_TO _output_cyan = @Evaluate((1-@Value(_input_red)-@Value(_output_key))/(1-@Value(_output_key)))
      SET_TO _output_magenta = @Evaluate((1-@Value(_input_green)-@Value(_output_key))/(1-@Value(_output_key)))
      SET_TO _output_yellow = @Evaluate((1-@Value(_input_blue)-@Value(_output_key))/(1-@Value(_output_key)))
    -> AttributeRounder
AttributeManager_11
    ATTR_TABLE:
      SET_TO _output_key = @Evaluate((1-@max(@Value(_input_red),@Value(_input_green),@Value(_input_blue)))*100)
      SET_TO _output_cyan = @Evaluate(((1-@Value(_input_red)-@Value(_output_key))/(1-@Value(_output_key)))*100)
      SET_TO _output_magenta = @Evaluate(((1-@Value(_input_green)-@Value(_output_key))/(1-@Value(_output_key)))*100)
      SET_TO _output_yellow = @Evaluate(((1-@Value(_input_blue)-@Value(_output_key))/(1-@Value(_output_key)))*100)
    -> AttributeRounder
AttributeRounder
    PLACES = 2
    ROUND_TYPE = Nearest
    SRC_ATTRS = _output_cyan _output_key _output_yellow _output_magenta
    -> AttributeManager_12
AttributeManager_12
    ATTR_TABLE = SET_TO _output_color = @Value(_output_cyan),@Value(_output_magenta),@Value(_output_yellow),@Value(_output_key)
    -> Output (output)
