FME workspace ff391911_LeBonFME.fmw

Parameters:
- DestDataset_POSTGIS =
- SourceDataset_GEOJSON =
- SourceDataset_GEOJSON_3 =

Readers:
- GEOJSON_1: GEOJSON from $(SourceDataset_GEOJSON)
- GEOJSON_2: GEOJSON from $(SourceDataset_GEOJSON_3)

Writers:
- POSTGIS_1: POSTGIS to $(DestDataset_POSTGIS)

OCcupation commerciale 2022 (reader GEOJSON_1)
    attributes: ID string, ORIGINE string, T_COMMERCE string, DATE_RECENSEMENT string, CIVIQUE string, TYPE_VOIE string, LIEN_VOIE string, NOM_VOIE string, ORIENTATION string, ADRESSE string, SUITE string, CODE_POST string, ETAGE string, NOM_CENTRE string, NOM_ETAB string, ID_USAGE1 string, USAGE1 string, ID_USAGE2 string, USAGE2 string, ID_USAGE3 string, USAGE3 string, SCIAN string, SITEWEB string, SITE_TRANSACTIONNEL string, ACCES_MOBILITE_REDUITE string, VACANT_A_LOUER string, A_LOUER_CONTACT string, A_LOUER_TELEPHONE string, ARRONDISSEMENT string, QUARTIER string,
      SDC_NOM string, SECTEUR_PME string, ENFANT string, MULTIUSAGE string, MULTIOCCUPANT string, NEQ string, SUFFIXE_NEQ string, COORDX string, COORDY string, LAT string, LONG string
    -> VertexCreator
VertexCreator
    MEASURE_TYPE = Continuous
    MODE_NAME = Replace with Point
    XVAL = @Value(LONG)
    YVAL = @Value(LAT)
    -> AttributeFilter
    <REJECTED> -> VertexCreator__Rejected_
AttributeFilter
    ATTR_NAME = USAGE1
    ATTR_VALUES = <Empty>,<Missing>,<Null>,<Unfiltered>,VACANT
    VACANT -> PointOnAreaOverlayer [POINT]
VertexCreator__Rejected_: Logger
    LOG_FEATURE = LOG_ONLY
    MAXCOORDS = 20
    MAXFEATS = 20
    MESSAGE = Feature is:
    SEVERITY = INFO
limites-terrestres (reader GEOJSON_2)
    attributes: DefaultAtt string
    -> H3HexagonalIndexer
H3HexagonalIndexer
    INDEX_OPERATION = Filling Indexes
    -> PointOnAreaOverlayer [AREA]
    <REJECTED> -> H3HexagonalIndexer__Rejected_
PointOnAreaOverlayer
    ATTR_ACCUM_MODE = Merge Incoming
    ATTR_CONFLICT_RES = Use Original
    DEAGGREGATE_INPUT = Yes
    OV_ATTR = nb_vacant
    POLYS_FIRST = NO
    AREA -> AttributeKeeper
    <REJECTED> -> PointOnAreaOverlayer__Rejected_
AttributeKeeper
    CREATE_BULK_MODE_FEATURES = NO
    KEEP_ATTRS = _h3index,nb_vacant
    -> ff391911 (writer POSTGIS_1)
ff391911 (writer POSTGIS_1)
    attributes: _h3index numeric(20,0), nb_vacant int8
PointOnAreaOverlayer__Rejected_: Logger
    LOG_FEATURE = LOG_ONLY
    MAXCOORDS = 20
    MAXFEATS = 20
    MESSAGE = Feature is:
    SEVERITY = INFO
H3HexagonalIndexer__Rejected_: Logger
    LOG_FEATURE = LOG_ONLY
    MAXCOORDS = 20
    MAXFEATS = 20
    MESSAGE = Feature is:
    SEVERITY = INFO
